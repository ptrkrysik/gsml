CISCO-GP10-MIB

-- Title	CISCO MNET GP10 MIB version 1.0
-- Note		JetCell has been acquired by Cisco, so the organization is Cisco, 
--			but we still use JetCell's org-number

-- Necessary Wind Riverism's to make the mib compiler work properly

--FORCE-INCLUDE <mib.h>
--FORCE-INCLUDE <snmpdefs.h>
--FORCE-INCLUDE "mibhand.h"
--FORCE-INCLUDE "mibleaf.h"
--FORCE-INCLUDE "mibtags.h"

--DEFAULT get-function-async	_snmp_getMethod
--DEFAULT next-function-async	_snmp_nextMethod
--DEFAULT set-function-async	_snmp_setMethod
--DEFAULT test-function-async	_snmp_testMethod
--DEFAULT cookie		MIB_%n

	DEFINITIONS ::= BEGIN

IMPORTS
	MODULE-IDENTITY, OBJECT-TYPE, NOTIFICATION-TYPE, IpAddress
		FROM SNMPv2-SMI
	DisplayString
		FROM RFC1213-MIB
	enterprises, Gauge
		FROM RFC1155-SMI
	;

jetcell MODULE-IDENTITY
	LAST-UPDATED "9904010000Z"
	ORGANIZATION "JetCell, Inc."
	CONTACT-INFO
		"	Technical Support
			Postal: JetCell, Inc.
				173 Constitution Drive
				Menlo Park, CA  94025
				USA

			Tel:	+1 650 330 2800
			Fax:	+1 650 330 1390

			Email:	support@jetcell.com"
	DESCRIPTION
		"This is the MIB definition for the JetCell ViperCell
		wireless base station. This includes leafs for the GSM,
		H.323, configuration and other MIB variables."
	::= {enterprises 3583}

-- Textual Conventions used in the GSM SMI
-- The following define the type of data that is represented in the MIB.

-- TBCD-STRING			::= OCTET STRING

AbsoluteRFChannelNo		::= INTEGER (0..1023)
AveragingNumber			::= INTEGER (0..31)
CauseCode			::= INTEGER
CellIdentity			::= INTEGER (0..65535)
CellReselectHysteresis		::= INTEGER (0..7)
ChannelID			::= INTEGER (0..7)
ClassNumber			::= INTEGER (0..15)
FrequencyUsage			::= INTEGER
GSMGeneralObjectID		::= INTEGER
HoMargin			::= INTEGER (0..24) -- db
HoPriorityLevel 		::= INTEGER (0..7)
HoppingSequenceNumber		::= INTEGER (0..63)
L2Timer				::= INTEGER
L3Timer				::= INTEGER
HandoverTimer			::= INTEGER
LocationAreaCode		::= INTEGER (0..65535)
MaxQueueLength			::= INTEGER (0..100)
MobileCountryCode		::= 
    -- mobile country code: 3 digit in decimal which is saved in INTEGER variable in 
	-- BCD format
    --   B[12..31]: 0(don't care)
    --   B[8..11]:  1st digit(most significant digit), valid range 0 ~ 9
    --   B[4..7]:   2nd digit, valid range 0 ~ 9
    --   B[0..3]:   3rd digit(least significant digit), valid range 0 ~ 9
    INTEGER

MobileNetworkCode		::= 
    -- mobile network code: 2 or 3 digit in decimal which is saved in INTEGER variable 
	-- in BCD format except last digit which may have 0xf
    --   B[12..31]: 0(don't care)
    --   B[8..11]:  1st digit(most significant digit), valid range 0 ~ 9
    --   B[4..7]:   2nd digit, valid range 0 ~ 9
    --   B[0..3]:   3rd digit(least significant digit), valid range 0 ~ 9 or 0xf
    -- if last digit has 0xf, then MNC is 2 digit, else if it has 0 ~ 9 then MNC is 
	-- 3 digit.
	INTEGER

MSRangeMax			::= INTEGER
NetworkColourCode		::= INTEGER (0..7)
NoOfBlocksForAccessGrant	::= INTEGER (0..7)
NoOfMultiframesBetweenPaging	::= INTEGER (2..9)
Ny1				::= INTEGER (0..7)
PlmnPermitted			::= INTEGER
PowerControlInterval		::= INTEGER (0..31)
PowerIncrStepSize		::= INTEGER (0..2)
PowerRedStepSize		::= INTEGER (0..1)
QueueTimeLimit			::= INTEGER
RadioLinkTimeout		::= INTEGER (0..15)
RxLev				::= INTEGER (0..63)
RxQual				::= INTEGER (0..7)
TimerPeriodicUpdateMS		::= INTEGER (0..255)
Tsc				::= INTEGER
TxInteger			::= INTEGER (0..15)
TxPower				::= INTEGER
TxPwrMaxReduction		::= INTEGER (0..6)
Weighting			::= INTEGER (0..3)

Si13Position		::= INTEGER (0..1)
CbchTrxSlot			::= INTEGER (0..7)
CbchTrx				::= INTEGER (0..1)
BcchChangeMark		::= INTEGER (0..3)
SiChangeField		::= INTEGER (0..15)



-- DisplayString			::= OCTET STRING (SIZE(0..255))
-- Complex variables:
-- Average				::= INTEGER
-- Deviation			::= INTEGER
-- Minimum			::= INTEGER
-- Maximum			::= INTEGER
--
-- The following textual conventions limit the value to particular items.
-- This is very much like the C "typedef enum" construct.
--

AdministrativeState	::= INTEGER { locked(0), unlocked(1), shuttingDown(2) }
AlarmStatus		::= INTEGER { underRepair(0), critical(1), major(2),
				      minor(3), alarmOutstanding(4) }
Boolean			::= INTEGER { false(0), true(1) }
ChannelCombination	::= INTEGER { tCHFull(0),  -- TCH/F + FACCH/F + SACCH/F
				      tCHHalf(1),  -- TCH/H(0,1) + FACCH/H(0,1) + SACCH/H(0,1)
				      tCHHalf2(2), -- TCH/H(0,0) + FACCH/H(0,1) + SACCH/H(0,1) + TCH/H(1,1)
				      sDCCH(3),    -- SDCCH/8(0 ..7) + SACCH/C8(0 .. 7)
				      mainBCCH(4), -- FCCH + SCH + BCCH + CCCH
				      bCCHCombined(5),	-- FCCH + SCH + BCCH + CCCH + SDCCH/4(0...3) + SACCH/C4(0...3)
				      cCH(6),	   -- BCCH + CCCH
				      bCCHwithCBCH(7),	-- combination 5 with CBCH as 05.02 Note 1
				      sDCCHwithCBCH(8)	-- combination 3 with CBCH as 05.02 Note 1
				    }

DtxUplink		::= INTEGER { msMayUseDTx(0), msShallUseDTx(1),
				      msShallNotUseDTx(2) }
EnableHoType		::= INTEGER { enablePwrBudget(0),
				      enableMSDistanceProcess (1) }
EnableDisable		::= INTEGER { disable(0), enable(1) }
GsmdcsIndicator		::= INTEGER { gsm(0), dcs(1), pcs1900(2)}
LoopBackControlCode	::= INTEGER { disable(0), enable(1) }
MaxRetrans		::= INTEGER { one(1), two(2), four(4), seven(7) }
OperationalState	::= INTEGER { disabled(0), enabled(1) }
OamCommand		::= INTEGER {
                      none                (0),  -- No OAM activity
				      reloadMib           (1),  -- Load MIB from the default MIB file.
				      flushMib            (2),  -- Save MIB to the default MIB file.
				      loadMibFromAltFile  (4),  -- Load MIB from an alternate MIB file.
				      saveMibToAltFile    (8),  -- Save MIB to the alternate MIB file.
				      saveMibMinDelay     (16), -- Save MIB to the disk as soon as possible. It may incuur excessive number of FILE I/O if the changes are fequentnt
				      saveMibMinFileIo    (32), -- Save MIB with some delay, but less Filo I/O. Multiple changes may be handled with one File I/O
				      reboot              (64), -- Reboot the node immidiately.
				      delayedReboot       (128) -- Reboot the node in 30 second time.
				    }
OamCommandExecutionStatus ::= INTEGER { none (0),
				      inProgress (1), -- OAM Command is in progress. 
				      sucessful	 (2), -- Last OAM command was completed successfully
				      failed	 (3)  -- Last OAM command execution failed. Check oamCommandLastError to get text description of the error
				    }

PowerClass		::= INTEGER {
					  m1 (1), -- (0.2W - GSM 900)
					  m3 (2), -- (0.1W - DCS 1800)
					  m2 (3)  -- (0.2W - PCS 1900)
				    }
SnmpTrapType		::= INTEGER {
				     snmpv1Trap (1),
				     snmpv2Trap (2)
				    }
--SnmpTrigger		::= INTEGER {
--				     none (0),
--				     when-item-1-changes (1),
--				     when-item-2-changes (2),
--				     when-item-1-or-2-changes (3),
--				     when-item-1-exceeds-item-2 (4),
--				     once-when-item-1-changes (5),
--				     once-when-item-2-changes (6),
--				     once-when-item-1-or-2-changes (7),
--				     once-when-item-1-exceeds-item-2 (8)
--				    }

PowerStatus		::= INTEGER { power-off(0), power-on(1) }
PowerSupplyType		::= INTEGER { basic(0), ups(1) }
RecoveryMode		::= INTEGER { disable(0), enable(1), now(2) }

gp10Mib				OBJECT IDENTIFIER ::= { jetcell 1 }
gmcMib				OBJECT IDENTIFIER ::= { jetcell 2 }
viperAccessMib		OBJECT IDENTIFIER ::= { jetcell 3 } 

gp10GsmMib			OBJECT IDENTIFIER ::= { gp10Mib 1 }
gp10H323Mib			OBJECT IDENTIFIER ::= { gp10Mib 2 }
gp10ConfigMib		OBJECT IDENTIFIER ::= { gp10Mib 3 }
gp10SpecificMib		OBJECT IDENTIFIER ::= { gp10Mib 4 }
gp10MgmtInfoMib		OBJECT IDENTIFIER ::= { gp10Mib 5 }
gp10ErrorInfoMib	OBJECT IDENTIFIER ::= { gp10Mib 6 }
gp10GprsMib			OBJECT IDENTIFIER ::= { gp10Mib 7 }  -- Sandeep
gp10CdrMib			OBJECT IDENTIFIER ::= { gp10Mib 8 }
handoverTimerMib	OBJECT IDENTIFIER ::= { gp10Mib 9 }
gp10ServiceStatusMib OBJECT IDENTIFIER ::= { gp10Mib 10 } 

--
--	gp10 MIB
--
--	The Gp10 MIB is organized into 3 sub-leafs. The first contains
--	a consolidation of information based on the CMIP/CMISE GSM definitions
--	in the GSM 12.xx specifications. The second leaf contains information
--	from the public H.323 MIB definitions. The third contains configuration
--	parameters and data that is required for the Gp10 to initialize.
--
--	Initially, only the gp10GsmMib and the gp10ConfigMib leafs
--	of the MIB are defined. As the H.323 specifications are formalized
--	the H.323 values will be added. Note: Initialization parameters for
--	the H.323 stack are stored in a leaf under gp10ConfifMib.
--
--
--	The gp10GsmMib is largest and most complex part of the MIB that
--	is currently defined. It is broken into several leafs as follows: 
--
--	1:	btsBasicPackage			Basic Parameters (primarily RM)
--	2:	btsOptionsPackage		More params (wider interest)
--	3:	firstTransceiverPackage		All the per-transceiver parms
--	4:	secondTransceiverPackage	Exact duplicate for 2nd trx.
--	5:	firstRadioCarrierPackage	The radio carrier information.
--	6:	secondRadioCarrierPackage	Exact duplicate for 2nd trx.
--	7:	btsTimerPackage			General timers used.
--	8:	adjacentCellPackage		Adj Cell Handover & Reselection
--	9:	frequencyHoppingPackage		Frequency Hopping params
--	10:	handoverControlPackage		Handover control params
--	11:	powerControlPackage		Power control params
--	12:	cellMeasurmentPackage		Performance measurment data
--	13:	callControlMeasurmentPackatge	More performance data.
--

btsBasicPackage OBJECT IDENTIFIER
-- 	DESCRIPTION
-- 		"The bts MOC represents the GSM functional element Base
-- 		 Transceiver Station. An instance of this MOC is associated
-- 		 by containment with a particular bssFunction instance and a
-- 		 particular btsSiteManager instance. Multiple instances of
-- 		 this MOC may be contained within a btsSiteManager instance.
-- 		 The attributes within the package btsBasicPackage describe
-- 		 the basic properties of a BTS that are not related to the
-- 		 Common Control Channels.
-- 
-- 		 The attributes bsIdentityCode and cellGlobalIdentity can be
-- 		 modified by the M-SET command only when the administrative
-- 		 state of the bts is locked.
-- 
-- 		 All values of the administrative, operational, and usage
-- 		 states are supported. The availabilityStatus qualifies in
-- 		 more details the operationalState while the controlStatus
-- 		 provides information to support the test management. The
-- 		 M-SET command changing the administrative state shall not
-- 		 change any other attributes.
-- 
-- 		 The administrative states for the BTS have the following
-- 		 meanings: In the shutting down state, no new traffic is
-- 		 allowed through the BTS. In this state, the BTS is barred
-- 		 (message sent to MS) and no incoming handovers are allowed.
-- 		 If all traffic is cleared, the BTS changes to the locked
-- 		 state. In the locked state, all calls through the BTS are
-- 		 disconnected. The BSC should clear all calls with cause set
-- 		 to 'O and M intervention'. No new traffic is possible on the
-- 		 BTS and no incoming handovers are allowed. In the unlocked
-- 		 state, new traffic is allowed through the BTS and incoming
-- 		 handovers are allowed. The locked administrative state stops
-- 		 normal operations of the resource (not, for example,
-- 		 operations for test purposes)."
	::= {gp10GsmMib 1}

	bts-ncc	OBJECT-TYPE
	    SYNTAX	NetworkColourCode
	    MAX-ACCESS	read-write
	    STATUS	current
	    DESCRIPTION
		"This attribute contains the Base Station Identity Code (BSIC),
		which is transmitted on the SCH and used for identifying a BTS.
		The BSIC consists of the Network Colour Code (NCC) and the Base
		Station Colour Code (BCC). Refer to Specification GSM 04.08."
	    REFERENCE
		"Owner Module: RRM module
		Mode-of-operation: set from manager
		Effective-time: next restart"
	    ::= {btsBasicPackage 1}

	bts-cid	OBJECT-TYPE
	    SYNTAX	CellIdentity
	    MAX-ACCESS	read-write
	    STATUS	current
	    DESCRIPTION
		"Mobile Network Code"
	    REFERENCE
		"Owner Module: RRM module
		Mode-of-operation: set from manager
		Effective-time: next restart"
	    ::= {btsBasicPackage 2}

	btsID	OBJECT-TYPE
	    SYNTAX	GSMGeneralObjectID
	    MAX-ACCESS	read-write
	    STATUS	current
	    DESCRIPTION
		"This attribute names a bts object. Its value is an
		 integral number, which must be unique within the
		 superior btsSiteManager."
	    REFERENCE
		"Owner Module: RRM module
		Mode-of-operation: set from manager
		Effective-time: next restart"
	    ::= {btsBasicPackage 3}

	cellAllocationTable	OBJECT-TYPE
	    SYNTAX	SEQUENCE OF CellAllocationEntry
	    MAX-ACCESS	not-accessible
	    STATUS	current
	    DESCRIPTION
		"This entry is required to define a table of values."
	    REFERENCE
		"Owner Module: RRM module
		Mode-of-operation: set from manager
		Effective-time: next restart"
	    ::= {btsBasicPackage 4}

	cellAllocationEntry	OBJECT-TYPE
	    SYNTAX	CellAllocationEntry
	    MAX-ACCESS	not-accessible
	    STATUS	current
	    DESCRIPTION
		"This attribute defines the set of radio frequencies
		 allocated and available to a cell. The first element
		 sets the BCCH frequency."
	    REFERENCE
		"Owner Module: RRM module
		Mode-of-operation: set from manager
		Effective-time: next restart"
	    INDEX	{cellAllocationIndex}
	    --DEFAULT cookie MIBT_%n
	    ::= {cellAllocationTable 1}

	CellAllocationEntry	::= SEQUENCE {
	    cellAllocationIndex		INTEGER,
	    cellAllocation		AbsoluteRFChannelNo
	}

	cellAllocationIndex	OBJECT-TYPE
	    SYNTAX	INTEGER (0..31)
	    MAX-ACCESS	read-only
	    STATUS	current
	    DESCRIPTION
		"Index to the Cell Allocation table."
	    REFERENCE
		"Owner Module: RRM module
		Mode-of-operation: set from manager
		Effective-time: next restart"
	    ::= {cellAllocationEntry 1}

	cellAllocation	OBJECT-TYPE
	    SYNTAX	AbsoluteRFChannelNo
	    MAX-ACCESS	read-write
	    STATUS	current
	    DESCRIPTION
		"This attribute contains a radio frequency that is allocated
		 and available to this cell."
	    REFERENCE
		"Owner Module: RRM module
		Mode-of-operation: set from manager
		Effective-time: next restart"
	    ::= {cellAllocationEntry 2}

	gsmdcsIndicator		OBJECT-TYPE
	    SYNTAX	GsmdcsIndicator
	    MAX-ACCESS	read-write
	    STATUS	current
	    DESCRIPTION
		"This attribute indicates the type (GSM or DCS 1800) of
		 the cell. The value may be used to interpret or check
		 other attribute values."
	    REFERENCE
		"Owner Module: RRM module
		Mode-of-operation: set from manager
		Effective-time: next restart"
	   ::= {btsBasicPackage 5}

	bts-mcc	OBJECT-TYPE
	    SYNTAX	MobileCountryCode
	    MAX-ACCESS	read-write
	    STATUS	current
	    DESCRIPTION
		"This attribute contains the Cell Identification (CI) and
		the Location Area of the cell. A Location Area  is unique
		within a GSM PLMN; a Cell Identification is unique within
		a location area. For further details see Spec GSM 03.03.
		
		MobileCountryCode

		Note: 3 digit in decimal which is saved in INTEGER variable in BCD format
		     B[12..31]: 0(don't care)
		     B[8..11]:  1st digit(most significant digit), valid range 0 ~ 9
		     B[4..7]:   2nd digit, valid range 0 ~ 9
		     B[0..3]:   3rd digit(least significant digit), valid range 0 ~ 9
		"
	    REFERENCE
		"Owner Module: RRM + CC + MM module
		Mode-of-operation: set from manager
		Effective-time: next restart"
	    ::= {btsBasicPackage 6}

	bts-mnc	OBJECT-TYPE
	    SYNTAX	MobileNetworkCode
	    MAX-ACCESS	read-write
	    STATUS	current
	    DESCRIPTION
		"Mobile Network Code
		
		Note: 2 or 3 digit in decimal which is saved in INTEGER variable in BCD format except last digit which may have 0xf
		     B[12..31]: 0(don't care)
		     B[8..11]:  1st digit(most significant digit), valid range 0 ~ 9
		     B[4..7]:   2nd digit, valid range 0 ~ 9
		     B[0..3]:   3rd digit(least significant digit), valid range 0 ~ 9 or 0xf
		     if last digit has 0xf, then MNC is 2 digit, else if it has 0 ~ 9 then MNC is 3 digit.
		"
	    REFERENCE
		"Owner Module: RRM + CC + MM module
		Mode-of-operation: set from manager
		Effective-time: next restart"
	    ::= {btsBasicPackage 7}

	bts-lac	OBJECT-TYPE
	    SYNTAX	LocationAreaCode
	    MAX-ACCESS	read-write
	    STATUS	current
	    DESCRIPTION
		"Location Area Code"
	    REFERENCE
		"Owner Module: RRM + CC + MM module
		Mode-of-operation: set from manager
		Effective-time: next restart"
	    ::= {btsBasicPackage 8}

	bts-ci	OBJECT-TYPE
	    SYNTAX	CellIdentity
	    MAX-ACCESS	read-write
	    STATUS	current
	    DESCRIPTION
		"Cell Identity Code"
	    REFERENCE
		"Owner Module: RRM + CC + MM module
		Mode-of-operation: set from manager
		Effective-time: next restart"
	    ::= {btsBasicPackage 9}

	cellReselectHysteresis	OBJECT-TYPE
	    SYNTAX	CellReselectHysteresis
	    MAX-ACCESS	read-write
	    STATUS	current
	    DESCRIPTION
		"The cell-reselect-hysteresis attribute indicates the
		 value of the receiver RF power level hysteresis required
		 for cell reselection. Refer to Specification GSM 05.08.

		 This parameter has a range of 0 to 14 dB with a step size
		 of 2 dB and is coded as an integer in the range 0 to 7
		 representing the number of the 2 dB steps."
	    REFERENCE
		"Owner Module: RRM module
		Mode-of-operation: set from manager
		Effective-time: next restart"
	   ::= {btsBasicPackage 10}

	ny1		OBJECT-TYPE
	    SYNTAX	Ny1
	    MAX-ACCESS	read-write
	    STATUS	current
	    DESCRIPTION
		"The ny1 attribute indicates the maximum number of
		 repetitions of the PHYSICAL INFORMATION message on the
		 radio interface (GSM 04.08). This message is sent by the
		 BTS to the MS during a handover procedure between two not
		 synchronized cells, in order to establish a physical channel
		 connection on the new cell."
	    REFERENCE
		"Owner Module: RRM module
		Mode-of-operation: set from manager
		Effective-time: next restart"
	   ::= {btsBasicPackage 11}

	plmnPermittedTable	OBJECT-TYPE
	    SYNTAX	SEQUENCE OF PlmnPermittedEntry
	    MAX-ACCESS	not-accessible
	    STATUS	current
	    DESCRIPTION
		"This attribute contains the values of the Network Colour
		 Code (NCC) for an accessing MS. Refer to Specification
		 GSM 05.08 (NCC_PERMITTED)."
	    REFERENCE
		"Owner Module: RRM module
		Mode-of-operation: set from manager
		Effective-time: next restart"
	    ::= {btsBasicPackage 12}

	plmnPermittedEntry	OBJECT-TYPE
	    SYNTAX	PlmnPermittedEntry
	    MAX-ACCESS	not-accessible
	    STATUS	current
	    DESCRIPTION
		"This entry is required to define a table of values."
	    REFERENCE
		"Owner Module: RRM module
		Mode-of-operation: set from manager
		Effective-time: next restart"
	    INDEX	{plmnPermittedIndex}
	    --DEFAULT cookie MIBT_%n
	    ::= {plmnPermittedTable 1}

	PlmnPermittedEntry	::= SEQUENCE {
	    plmnPermittedIndex		INTEGER,
	    plmnPermitted		PlmnPermitted
	}

	plmnPermittedIndex	OBJECT-TYPE
	    SYNTAX	INTEGER
	    MAX-ACCESS	read-only
	    STATUS	current
	    DESCRIPTION
		"Index to the Plmn Permitted table."
	    REFERENCE
		"Owner Module: RRM module
		Mode-of-operation: set from manager
		Effective-time: next restart"
	    ::= {plmnPermittedEntry 1}

	plmnPermitted	OBJECT-TYPE
	    SYNTAX	PlmnPermitted
	    MAX-ACCESS	read-write
	    STATUS	current
	    DESCRIPTION
		"This attribute contains the values of the Network Colour
		 Code (NCC) for an accessing MS. Refer to Specification
		 GSM 05.08 (NCC_PERMITTED)."
	    REFERENCE
		"Owner Module: RRM module
		Mode-of-operation: set from manager
		Effective-time: next restart"
	    ::= {plmnPermittedEntry 2}

	radioLinkTimeout	OBJECT-TYPE
	    SYNTAX	RadioLinkTimeout
	    MAX-ACCESS	read-write
	    STATUS	current
	    DESCRIPTION
		"The radioLinkTimeout attribute is used to indicate the
		 maximum value of the radio link counter needed to detect
		 a radio link failure. This value is used by the MS
		 procedure and may also be used for the BSS procedure.
		 See Specification GSM 05.08  for more information. This
		 attribute corresponds to the radio sub-system link control
		 parameter RADIO_LINK_TIMEOUT.

		 The radio-link-time-out parameter has a range from 4 to
		 64 SACCH blocks with a step size of 4 SACCH blocks."
	    REFERENCE
		"Owner Module: L1 module
		Mode-of-operation: set from manager
		Effective-time: next restart"
		DEFVAL
		{4}
	    ::= {btsBasicPackage 13}

	relatedTranscoder	OBJECT-TYPE
	    SYNTAX	GSMGeneralObjectID
	    MAX-ACCESS	read-write
	    STATUS	current
	    DESCRIPTION
		"The relatedTranscoder indicates the instance(s) of
		 the transcoder object (if any) that are related to
		 a bts for purposes of TRAU O&M messages as specified
		 in GSM 08.60 and GSM 12.21."
	    REFERENCE
		"Owner Module: L1 module
		Mode-of-operation: set from manager
		Effective-time: next restart"
	   ::= {btsBasicPackage 14}

	rxLevAccessMin	OBJECT-TYPE
	    SYNTAX	RxLev
	    MAX-ACCESS	read-write
	    STATUS	current
	    DESCRIPTION
		"The rxLevAccessMin attribute is used to indicate the
		 minimum receive level at the MS required for access
		 to the system. See Specification GSM 05.08
		 (RXLEV_ACCESS_MIN). This parameter is used in order
		 to evaluate the path loss criterion parameter (C1)
		 of a cell (GSM 05.08). The value is an integer in
		 the range 0 to 63 (GSM 05.08)."
	    REFERENCE
		"Owner Module: RRM module
		Mode-of-operation: set from manager
		Effective-time: next restart"
	   ::= {btsBasicPackage 15}

	bts-administrativeState	OBJECT-TYPE
	    SYNTAX	AdministrativeState
	    MAX-ACCESS	read-write
	    STATUS	current
	    DESCRIPTION
		"The semantics of the administrativeState attribute type are
		 specified in Recommendation X.731 and the syntax is defined
		 in Recommendation X.721.

		 This attribute has a value of locked(0), unlocked(1),
		 shuttingDown(2)."
	    REFERENCE
		"Owner Module: RRM module
		Mode-of-operation: set from manager
		Effective-time: immediatly"
	   ::= {btsBasicPackage 16}

	bts-alarmStatus	OBJECT-TYPE
	    SYNTAX	AlarmStatus
	    MAX-ACCESS	read-write
	    STATUS	current
	    DESCRIPTION
		"The semantics and syntax of the alarmStatus attribute type
		 are specified in Recommendation M.3100.

		 This attribute has a value of underRepair(0), critical(1),
		 major(2), minor(3), alarmOutstanding(4)."
	    REFERENCE
		"Owner Module: RRM module
		Mode-of-operation: set from RRM
		Effective-time: immediatly"
	    ::= {btsBasicPackage 17}

	bts-operationalState	OBJECT-TYPE
	    SYNTAX	OperationalState
	    MAX-ACCESS	read-write
	    STATUS	current
	    DESCRIPTION
		"The semantics of the operationalState attribute type is
		 specified in Recommendation X.731. A specification of the
		 syntax is found in Recommendation X.721.

		 This attribute has a value of disabled(0), enabled(1)."
	    REFERENCE
		"Owner Module: RRM module
		Mode-of-operation: set from RRM
		Effective-time: immediatly"
	   ::= {btsBasicPackage 18}

-- 	Bts CCCH Configuration Package
--	This package was consolidated with the BtsBasicPackage to
--	reduce the number of packages and hence the number of callbacks
--	in the SNMP manager.
--
-- btsCCCHConfigurationPackage OBJECT IDENTIFIER
-- 	DESCRIPTION
-- 		"The package btsCCCHConfigurationPackage defines the
-- 		 properties of the Common Control Channels of the BTS.
-- 		 All attribute values are broadcast to the Mobile Stations
-- 		 within the SYS INFO messages. Some of these may also be
-- 		 used by the BSS; e.g. to identify overload on the CCCH."
--
	maxNumberRetransmissions	OBJECT-TYPE
	    SYNTAX	MaxRetrans
	    MAX-ACCESS	read-write
	    STATUS	current
	    DESCRIPTION
		"The value of the attribute is the maximum number of
		 retransmissions a MS may perform on the RACH. The
		 possible values are 1, 2, 4 and 7. Refer to
		 Specification GSM 05.08 (MAX_RETRAN)."
	    REFERENCE
		"Owner Module: RRM module
		Mode-of-operation: set from manager
		Effective-time: next restart"
	    ::= {btsBasicPackage 19}

	mSTxPwrMaxCCH	OBJECT-TYPE
	    SYNTAX	TxPower
	    MAX-ACCESS	read-write
	    STATUS	current
	    DESCRIPTION
		"The mSTxPwrMaxCCH attribute is used to indicate the
		 maximum transmit power level a MS may use when accessing
		 the cell until commanded otherwise. See Specification
		 GSM 05.08 (MS_TXPWR_MAX_CCH). This parameter is also
		 used in order to evaluate the path loss criterion
		 parameter (C1) of a cell. See Specification GSM 05.08."
	    REFERENCE
		"Owner Module: RRM module
		Mode-of-operation: set from manager
		Effective-time: next restart"
	   ::= {btsBasicPackage 20}

	numberOfSlotsSpreadTrans	OBJECT-TYPE
	    SYNTAX	TxInteger
	    MAX-ACCESS	read-write
	    STATUS	current
	    DESCRIPTION
		"The numberOfSlotsSpreadTrans attribute (TX Integer) is
		 used to represent the maximum number of RACH slots a MS
		 must wait, after an unsuccessful random access attempt,
		 before a new random access. The MS draws a random number
		 between 0 and the value of this parameter, in order to
		 decide when to start the new access. Hence this parameter
		 allows the access retransmissions be spread over a fixed
		 number of RACH slots.

		 The value is coded as an integer in the range 0 to 15; the
		 corresponding numbers of slots used to spread transmission
		 (3 to 50) is indicated in Specification GSM 04.08."
	    REFERENCE
		"Owner Module: RRM module
		Mode-of-operation: set from manager
		Effective-time: next restart"
	   ::= {btsBasicPackage 21}

	noOfBlocksForAccessGrant	OBJECT-TYPE
	    SYNTAX	NoOfBlocksForAccessGrant
	    MAX-ACCESS	read-write
	    STATUS	current
	    DESCRIPTION
		"This attribute specifies the number of TDMA frames
		 reserved for the Access Grant channel during a period
		 of 51 TDMA frames (a multiframe). For details refer to
		 Specification GSM 05.02."
	    REFERENCE
		"Owner Module: RRM module
		Mode-of-operation: set from manager
		Effective-time: next restart"
	   ::= {btsBasicPackage 22}

	noOfMultiframesBetweenPaging	OBJECT-TYPE
	    SYNTAX	NoOfMultiframesBetweenPaging
	    MAX-ACCESS	read-write
	    STATUS	current
	    DESCRIPTION
		"This value denotes the number of multiframes (51 frames)
		 between two transmissions of the same paging message to
		 mobiles of the same paging group."
	    REFERENCE
		"Owner Module: RRM module
		Mode-of-operation: set from manager
		Effective-time: next restart"
	   ::= {btsBasicPackage 23}



btsOptionsPackage OBJECT IDENTIFIER
-- 	DESCRIPTION
-- 		"The package btsOptionsPackage defines the
-- 		 properties of the Common Control Channels of the BTS.
-- 		 All attribute values are broadcast to the Mobile Stations
-- 		 within the SYS INFO messages. Some of these may also be
-- 		 used by the BSS; e.g. to identify overload on the CCCH."
	::= {gp10GsmMib 2}

	allowIMSIAttachDetach	OBJECT-TYPE
	    SYNTAX	Boolean
	    MAX-ACCESS	read-write
	    STATUS	current
	    DESCRIPTION
		"This attribute controls whether the IMSI attach/detach
		 procedure is used in the cell. The value true means that
		 IMSI attach/detach is used. Ref. GSM 04.08."
	    REFERENCE
		"Owner Module: RRM + MM module
		Mode-of-operation: set from manager
		Effective-time: next restart"
	    ::= {btsOptionsPackage 1}

	callReestablishmentAllowed	OBJECT-TYPE
	    SYNTAX	Boolean
	    MAX-ACCESS	read-write
	    STATUS	current
	    DESCRIPTION
		"This attribute indicates whether call re-establishment
		 is allowed in the cell. A value of TRUE means that it
		 is allowed, a value of FALSE means not allowed."
	    REFERENCE
		"Owner Module: RRM + CC module
		Mode-of-operation: set from manager
		Effective-time: next restart"
	   ::= {btsOptionsPackage 2}

	cellBarred	OBJECT-TYPE
	    SYNTAX	Boolean
	    MAX-ACCESS	read-write
	    STATUS	current
	    DESCRIPTION
		"Cell Identity Code"
	    REFERENCE
		"Owner Module: RRM + CC + MM module
		Mode-of-operation: set from manager
		Effective-time: immediately"
	    ::= {btsOptionsPackage 3}

	dtxDownlink	OBJECT-TYPE
	    SYNTAX	Boolean
	    MAX-ACCESS	read-write
	    STATUS	current
	    DESCRIPTION
		"Availability of downlink DTX is an implementation option.
		 Its availability in a system is indicated by this attribute.
		 If available, use of the downlink DTX is controlled by the
		 MSC (see GSM 04.08). The boolean values of the dtxDownlink
		 attribute are as follows:

		 true = downlink DTX is available in the BTS
		 false = downlink DTX is not available in the BTS"
	    REFERENCE
		"Owner Module: RRM module
		Mode-of-operation: set from manager
		Effective-time: next restart"
	   ::= {btsOptionsPackage 4}

	dtxUplink	OBJECT-TYPE
	    SYNTAX	DtxUplink
	    MAX-ACCESS	read-write
	    STATUS	current
	    DESCRIPTION
		"This attribute specifies the Discontinuous Transmission
		 (DTX) mode to be used by the Mobile Stations. The
		 implementation of DTX for the uplink is compulsory
		 in the Mobile Station and the Base Station System.
		 However, its actual use is under control of the operator.
		 GSM 04.08 allows for three availability options to be
		 broadcast to the MS. The information as to whether a MS
		 can use uplink DTX is transmitted in the Cell Options of
		 the SYSINFO3 message. The alternatives are the following:

		-	Uplink DTX is on in the BTS and usage is under the
			control of the MS
			(MS may use DTX) 
		-	Uplink DTX is on in the BTS and all MSs must use it.
			(MS shall use DTX)
		-	Uplink DTX is off in the BTS.
			(MS shall not use DTX)"
	    REFERENCE
		"Owner Module: RRM module
		Mode-of-operation: set from manager
		Effective-time: next restart"
	   ::= {btsOptionsPackage 5}

	emergencyCallRestricted	OBJECT-TYPE
	    SYNTAX	Boolean
	    MAX-ACCESS	read-write
	    STATUS	current
	    DESCRIPTION
		"The attribute determines whether emergency calls are
		 allowed to all MSs or restricted to MSs belonging to
		 access classes in the range 11 to 15. The value true
		 indicates that emergency calls are restricted.

		 The special access class ten (10) is used to carry the
		 value on the Air Interface. See Specification 04.08."
	    REFERENCE
		"Owner Module: RRM module
		Mode-of-operation: set from manager
		Effective-time: next restart"
	   ::= {btsOptionsPackage 6}

	notAllowedAccessClassTable	OBJECT-TYPE
	    SYNTAX	SEQUENCE OF NotAllowedAccessClassEntry
	    MAX-ACCESS	not-accessible
	    STATUS	current
	    DESCRIPTION
		"The attribute determines whether emergency calls are
		 allowed to all MSs or restricted to MSs belonging to
		 access classes in the range 11 to 15. The value true
		 indicates that emergency calls are restricted.

		 The special access class ten (10) is used to carry the
		 value on the Air Interface. See Specification 04.08."
	    REFERENCE
		"Owner Module: RRM module
		Mode-of-operation: set from manager
		Effective-time: next restart"
	   ::= {btsOptionsPackage 7}

	notAllowedAccessClassEntry	OBJECT-TYPE
	    SYNTAX	NotAllowedAccessClassEntry
	    MAX-ACCESS	not-accessible
	    STATUS	current
	    DESCRIPTION
		"This entry is required to define a table of values."
	    REFERENCE
		"Owner Module: RRM module
		Mode-of-operation: set from manager
		Effective-time: next restart"
	    INDEX	{notAllowedAccessClassIndex}
	    --DEFAULT cookie MIBT_%n
	    ::= {notAllowedAccessClassTable 1}

	NotAllowedAccessClassEntry	::= SEQUENCE {
	    notAllowedAccessClassIndex	INTEGER,
	    notAllowedAccessClass	ClassNumber
	}

	notAllowedAccessClassIndex	OBJECT-TYPE
	    SYNTAX	INTEGER
	    MAX-ACCESS	read-only
	    STATUS	current
	    DESCRIPTION
		"Index to the not allowed access classes table."
	    REFERENCE
		"Owner Module: RRM module
		Mode-of-operation: set from manager
		Effective-time: next restart"
	    ::= {notAllowedAccessClassEntry 1}

	notAllowedAccessClass	OBJECT-TYPE
	    SYNTAX	ClassNumber
	    MAX-ACCESS	read-write
	    STATUS	current
	    DESCRIPTION
		"This attribute contains a list of MS Access Classes, which
		 are not allowed to access the cell. It should be noted that
		 the access class number ten (10) does not exist as a normal
		 access class; it is used to restrict emergency calls (see
		 also attribute emergencyCallRestricted). For further details
		 refer to Specification 04.08."
	    REFERENCE
		"Owner Module: RRM module
		Mode-of-operation: set from manager
		Effective-time: next restart"
	    ::= {notAllowedAccessClassEntry 2}

	timerPeriodicUpdateMS	OBJECT-TYPE
	    SYNTAX	TimerPeriodicUpdateMS
	    MAX-ACCESS	read-write
	    STATUS	current
	    DESCRIPTION
		"This specifies the interval for the MS periodic location
		 updates. The interval is measured in decihours; the range
		 is 0 to 255 decihours (25.5 hours). The value zero indicates
		 that the MS should not perform any periodic location updates."
	    REFERENCE
		"Owner Module: RRM module
		Mode-of-operation: set from manager
		Effective-time: next restart"
	   ::= {btsOptionsPackage 8}

--	BTS Queueing Package
--	This package was consolidated with the BtsOptionsPackage to
--	reduce the number of packages and hence the number of callbacks
--	in the SNMP manager.
--
-- btsQueueingPackage OBJECT IDENTIFIER
-- 	DESCRIPTION
-- 		"The attributes in the package btsQueuingPackage are
-- 		 parameters used in handling call and handover queues
-- 		 relevant to the BTS."

	maxQueueLength	OBJECT-TYPE
	    SYNTAX	MaxQueueLength
	    MAX-ACCESS	read-write
	    STATUS	current
	    DESCRIPTION
		"The attribute specifies the maximum length of queues in
		 the BTS. The queue elements are call and handover attempts
		 waiting for a TCH to be released in that BTS; the value is
		 a percentage of the total number of working TCHs in the BTS.

		 -	value 0:	no queuing used.
		 -	value 100: maximum queue length is equal to the
			total number of enabled TCHs."
	    REFERENCE
		"Owner Module: MM + CC module
		 Mode-of-operation: set from manager
		 Effective-time: next restart"
	    ::= {btsOptionsPackage 9}

	msPriorityUsedInQueueing	OBJECT-TYPE
	    SYNTAX	Boolean
	    MAX-ACCESS	read-write
	    STATUS	current
	    DESCRIPTION
		"This attribute specifies whether call  priority in
		 ASSIGNMENT REQUEST message (or HANDOVER REQUEST message
		 in ho) from MSC is taken into account in queue handling."
	    REFERENCE
		"Owner Module: MM + CC module
		 Mode-of-operation: set from manager
		 Effective-time: next restart"
	   ::= {btsOptionsPackage 10}

	timeLimitCall	OBJECT-TYPE
	    SYNTAX	QueueTimeLimit
	    MAX-ACCESS	read-write
	    STATUS	current
	    DESCRIPTION
		"This is the maximum time a call attempt may wait for a
		 traffic channel to be available (GSM 08.08 T11). The unit
		 of measure is seconds. The value zero indicates that no
		 call queuing is used in the BTS.

		 The value of this attribute is in seconds."
	    REFERENCE
		"Owner Module: MM + CC module
		 Mode-of-operation: set from manager
		 Effective-time: next restart"
	   ::= {btsOptionsPackage 11}

	timeLimitHandover	OBJECT-TYPE
	    SYNTAX	QueueTimeLimit
	    MAX-ACCESS	read-write
	    STATUS	current
	    DESCRIPTION
		"This is the maximum time a handover attempt may wait for
		 a traffic channel  to be available (GSM 08.08 Tqho). The
		 unit of measure is seconds. The value zero indicates that
		 no handover queuing is used in the BTS.

		 The value of this attribute is in seconds."
	    REFERENCE
		"Owner Module: MM + CC module
		 Mode-of-operation: set from manager
		 Effective-time: next restart"
	   ::= {btsOptionsPackage 12}


firstTransceiverPackage OBJECT IDENTIFIER
--
--	Tranceiver Package
--
--	There are several packages of data that need to be duplicated based
--	on the fact that there are 2 radios in the Gp10. Thus, we have
--	consolidated all of the data parameters that have to do with the
--	two transceivers into the following package. This includes the Baseband
--	tranceiver package, and the channel package.
--
--	Baseband Transceiver Package
--
-- basebandTransceiverPackage-0 OBJECT IDENTIFIER
-- 	DESCRIPTION
-- 		"The basebandTransceiver managed object class represents
-- 		 functions common to eight (8) channels which are mapped
-- 		 through the radio resource onto radio timeslots.  The
-- 		 underlying functionality to be managed includes speech
-- 		 rate adaptation, channel encoding and decoding, and frame
-- 		 building.
-- 
-- 		 This definition covers what may be described as the baseband
-- 		 aspects of transmission in the GSM and DCS 1800 base station
-- 		 systems. This functionality is related to the radio carrier
-- 		 aspects by means of the relatedRadioCarrier and the channel
-- 		 definitions (see radioCarrier and channel managed object
-- 		 classes). This package provides the basic set of attributes
-- 		 for identification and relationship management."
	::= {gp10GsmMib 3}

	basebandTransceiverID-0	OBJECT-TYPE
	    SYNTAX	GSMGeneralObjectID
	    MAX-ACCESS	read-write
	    STATUS	current
	    DESCRIPTION
		"This attribute names a baseband Transceiver."
	    REFERENCE
		"Owner Module: RRM module
		Mode-of-operation: set from manager
		Effective-time: immediatly"
	    ::= {firstTransceiverPackage 1}

	relatedRadioCarrier-0	OBJECT-TYPE
	    SYNTAX	GSMGeneralObjectID
	    MAX-ACCESS	read-write
	    STATUS	current
	    DESCRIPTION
		"This attribute identifies the instance of a radioCarrier
		 object which represents the RF aspects related to a
		 basebandTransceiver, if any. This attribute will take the
		 value 'NULL' when the basebandTransceiver object instance
		 has no direct relationship with any one radioCarrier object
		 instance (i.e. the timeslots handled by a basebandTransceiver
		 are possibly spread over several radioCarrier object
		 instances). "
	   ::= {firstTransceiverPackage 2}

	basebandAdministrativeState-0	OBJECT-TYPE
	    SYNTAX	AdministrativeState
	    MAX-ACCESS	read-write
	    STATUS	current
	    DESCRIPTION
		"The semantics of the administrativeState attribute type are
		 specified in Recommendation X.731 and the syntax is defined
		 in Recommendation X.721.

		 This attribute has a value of locked(0), unlocked(1),
		 shuttingDown(2)."
	    REFERENCE
		"Owner Module: RRM module
		Mode-of-operation: set from manager
		Effective-time: immediatly"
	   ::= {firstTransceiverPackage 3}

	basebandAlarmStatus-0	OBJECT-TYPE
	    SYNTAX	AlarmStatus
	    MAX-ACCESS	read-write
	    STATUS	current
	    DESCRIPTION
		"The semantics and syntax of the alarmStatus attribute type
		 are specified in Recommendation M.3100.

		 This attribute has a value of underRepair(0), critical(1),
		 major(2), minor(3), alarmOutstanding(4)."
	    REFERENCE
		"Owner Module: RRM module
		Mode-of-operation: set from RRM
		Effective-time: immediatly"
	    ::= {firstTransceiverPackage 4}


	basebandOperationalState-0	OBJECT-TYPE
	    SYNTAX	OperationalState
	    MAX-ACCESS	read-write
	    STATUS	current
	    DESCRIPTION
		"The semantics of the operationalState attribute type is
		 specified in Recommendation X.731. A specification of the
		 syntax is found in Recommendation X.721.

		 This attribute has a value of disabled(0), enabled(1)."
	    REFERENCE
		"Owner Module: RRM module
		Mode-of-operation: set from RRM
		Effective-time: immediatly"
	   ::= {firstTransceiverPackage 5}

--	Gp10	Channel Package
--
--	Note: There are 2 trx's on a viper cell, each with 8 channels.
--	Thus, this table was folded into the First and Second transceiver
--	data tables.
--
--
-- channelPackage OBJECT IDENTIFIER
-- 	DESCRIPTION
-- 		"The channel object class represents the manageable
-- 		 properties of a time slot. See Specification GSM 05.02
-- 		 for details. This package provides attributes for
-- 		 identification and management of the properties of the
-- 		 channel. A channel may or may not use frequency hopping.
-- 		 The usage of frequency hopping is indicated by the
-- 		 attribute frequencyUsage.
-- 
-- 		 The administrative states of the channel object have the
-- 		 following meanings: When a channel is locked it will
-- 		 immediately stop transmitting or receiving any information
-- 		 in the time slot. If the channel is a control channel, all
-- 		 calls in the BTS may be affected. When a channel is unlocked,
-- 		 it is able to accept traffic. When a channel is shutting down,
-- 		 no new traffic is allowed, no inbound handovers are accepted.
-- 		 In this state, clearing of existing traffic results in
-- 		 transition to locked state. The locked administrative state
-- 		 stops normal operations of the resource (not, for example,
-- 		 operations for test purposes)."
--	::= {gp10GsmMib 10}

	channel-0-Table	OBJECT-TYPE
	    SYNTAX	SEQUENCE OF Channel-0-Entry
	    MAX-ACCESS	not-accessible
	    STATUS	current
	    DESCRIPTION
		"This entry is required to define a table of values."
	    REFERENCE
		"Owner Module: RRM module
		Mode-of-operation: set from manager
		Effective-time: next restart"
	    ::= {firstTransceiverPackage 6}

	channel-0-Entry	OBJECT-TYPE
	    SYNTAX	Channel-0-Entry
	    MAX-ACCESS	not-accessible
	    STATUS	current
	    DESCRIPTION
		"This attribute defines the set of radio frequencies
		 allocated  and available to a cell. The first element
		 sets the BCCH frequency."
	    REFERENCE
		"Owner Module: RRM module
		Mode-of-operation: set from manager
		Effective-time: next restart"
	    INDEX	{channelIndex-0}
	    --DEFAULT cookie MIBT_%n
	    ::= {channel-0-Table 1}

	Channel-0-Entry	::= SEQUENCE {
	    channelIndex-0		 INTEGER,
	    channelID-0			 ChannelID,
	    channelCombination-0	 ChannelCombination,
	    channelFrequencyUsage-0	 FrequencyUsage,
	    channelTsc-0		 Tsc,
	    channelAdministrativeState-0 AdministrativeState,
	    channelOperationalState-0	 OperationalState
	}

	channelIndex-0	OBJECT-TYPE
	    SYNTAX	INTEGER (0..7)
	    MAX-ACCESS	read-only
	    STATUS	current
	    DESCRIPTION
		"This attribute is used as the index to this table. It
		 is a sequential number between 0 and 15."
	    REFERENCE
		"Owner Module: RRM module
		Mode-of-operation: set from manager
		Effective-time: next restart"
	    ::= {channel-0-Entry 1}

	channelID-0	OBJECT-TYPE
	    SYNTAX	ChannelID
	    MAX-ACCESS	read-write
	    STATUS	current
	    DESCRIPTION
		"This attribute is used for naming channel object
		 instances, and corresponds to the channel's time
		 slot number."
	    REFERENCE
		"Owner Module: RRM module
		 Mode-of-operation: set from manager
		 Effective-time: on restart"
	    ::= {channel-0-Entry 2}

	channelCombination-0	OBJECT-TYPE
	    SYNTAX	ChannelCombination
	    MAX-ACCESS	read-write
	    STATUS	current
	    DESCRIPTION
		"This attribute defines the logical channel combination
		 mapped onto the physical channel (time slot). For details
		 Refer to Specification GSM 05.02.

		 The following are the permitted ways, as defined by
		 GSM 04.03, in which channels can be combined onto basic
		 physical channels (numbers appearing in parenthesis after
		 channel designations indicate sub-channel numbers; channels
		 and sub-channels need not necessarily be assigned) :

		 i)	TCH/F + FACCH/F + SACCH/F
		 ii)	TCH/H(0,1) + FACCH/H(0,1) + SACCH/H(0,1)
		 iii)	TCH/H(0,0) + FACCH/H(0,1) + SACCH/H(0,1) + TCH/H(1,1)
		 iv)	FCCH + SCH + BCCH + CCCH
		 v)	FCCH + SCH + BCCH + CCCH + SDCCH/4(0...3) +  SACCH/C4(0...3)
		 vi)	BCCH + CCCH
		 vii)	SDCCH/8(0 ..7) + SACCH/C8(0 .. 7)
			where CCCH = PCH + RACH + AGCH 

		 Note 1: Where the SMSCB is supported, the CBCH replaces
			 SDCCH number 2 in cases v) and vii) above.
		 Note 2: A combined CCCH/SDCCH allocation (case v) above)
			 may only be used when no other CCCH channel is
			 allocated.
			 
		 *********************************************************************
		 WARNING: Currently(Ver 1.5, 2.0 and 3.0) the only valid value of 
			 Channel Combination of row 1 is BCCHCombined(5).
			 The only valid value of rest rows(row 2 to row 8) are TCHFull(0).
		 *********************************************************************"
	    REFERENCE
		"Owner Module: RRM module
		 Mode-of-operation: set from manager (only between combination I and V)
		 Effective-time: on restart"
	    ::= {channel-0-Entry 3}

	channelFrequencyUsage-0	OBJECT-TYPE
	    SYNTAX	FrequencyUsage
	    MAX-ACCESS	read-write
	    STATUS	current
	    DESCRIPTION
		"This attribute defines the frequencies used by a radio time
		 slot. If no frequency hopping is used, the attribute contains
		 an Absolute Radio Frequency Channel Number (ARFCN). If the
		 channel is configured to BCCH usage, the BCCH frequency is
		 set using the first value from the cellAllocation attribute
		 in the btsBasicPackage and the frequencyUsage attribute value
		 is ignored. If frequency hopping is used, the attribute
		 contains a reference to a frequencyHoppingSystem instance
		 plus the MAIO. ****"
	    REFERENCE
		"Owner Module: RRM module
		 Mode-of-operation: set from manager
		 Effective-time: on restart"
	    ::= {channel-0-Entry 4}

	channelTsc-0	OBJECT-TYPE
	    SYNTAX	Tsc
	    MAX-ACCESS	read-write
	    STATUS	current
	    DESCRIPTION
		"This attribute contains the Training Sequence Code (TSC)
		 of a radio channel. For control channels, TSC is always
		 equal to the BCC (Base Station Colour Code). For other
		 channels, there are no restrictions.
		 
		 *********************************************************************
		 WARNING: Currently(Ver 1.5, 2.0 and 3.0) the only valid value of 
			 this variable is 0(Use BCC).
		 *********************************************************************"
	    REFERENCE
		"Owner Module: RRM module
		 Mode-of-operation: set from manager
		 Effective-time: immediately"
	    ::= {channel-0-Entry 5}

	channelAdministrativeState-0	OBJECT-TYPE
	    SYNTAX	AdministrativeState
	    MAX-ACCESS	read-write
	    STATUS	current
	    DESCRIPTION
		"The semantics of the administrativeState attribute type are
		 specified in Recommendation X.731 and the syntax is defined
		 in Recommendation X.721.

		 This attribute has a value of locked(0), unlocked(1),
		 shuttingDown(2)."
	    REFERENCE
		"Owner Module: RRM module
		 Mode-of-operation: set from manager
		 Effective-time: immediately"
	   ::= {channel-0-Entry 6}

	channelOperationalState-0	OBJECT-TYPE
	    SYNTAX	OperationalState
	    MAX-ACCESS	read-write
	    STATUS	current
	    DESCRIPTION
		"The semantics of the operationalState attribute type is
		 specified in Recommendation X.731. A specification of the
		 syntax is found in Recommendation X.721.

		 This attribute has a value of disabled(0), enabled(1)."
	    REFERENCE
		"Owner Module: RRM module
		 Mode-of-operation: set from RRM
		 Effective-time: on restart"
	   ::= {channel-0-Entry 7}

secondTransceiverPackage OBJECT IDENTIFIER
--
--	Transceiver Package
--
--	There are several packages of data that need to be duplicated based
--	on the fact that there are 2 radios in the Gp10. Thus, we have
--	consolidated all of the data parameters that have to do with the
--	two transceivers into the following package. This includes the Baseband
--	Transceiver package, the radio carrier package and the channel package.
--
--	Baseband Transceiver Package
--
-- basebandTransceiverPackage-1 OBJECT IDENTIFIER
-- 	DESCRIPTION
-- 		"The basebandTransceiver managed object class represents
-- 		 functions common to eight (8) channels which are mapped
-- 		 through the radio resource onto radio timeslots.  The
-- 		 underlying functionality to be managed includes speech
-- 		 rate adaptation, channel encoding and decoding, and frame
-- 		 building.
-- 
-- 		 This definition covers what may be described as the baseband
-- 		 aspects of transmission in the GSM and DCS 1800 base station
-- 		 systems. This functionality is related to the radio carrier
-- 		 aspects by means of the relatedRadioCarrier and the channel
-- 		 definitions (see radioCarrier and channel managed object
-- 		 classes). This package provides the basic set of attributes
-- 		 for identification and relationship management."
	::= {gp10GsmMib 4}

	basebandTransceiverID-1	OBJECT-TYPE
	    SYNTAX	GSMGeneralObjectID
	    MAX-ACCESS	read-write
	    STATUS	current
	    DESCRIPTION
		"This attribute names a baseband Transceiver."
	    REFERENCE
		"Owner Module: RRM module
		Mode-of-operation: set from manager
		Effective-time: immediatly"
	    ::= {secondTransceiverPackage 1}

	relatedRadioCarrier-1	OBJECT-TYPE
	    SYNTAX	GSMGeneralObjectID
	    MAX-ACCESS	read-write
	    STATUS	current
	    DESCRIPTION
		"This attribute identifies the instance of a radioCarrier
		 object which represents the RF aspects related to a
		 basebandTransceiver, if any. This attribute will take the
		 value 'NULL' when the basebandTransceiver object instance
		 has no direct relationship with any one radioCarrier object
		 instance (i.e. the timeslots handled by a basebandTransceiver
		 are possibly spread over several radioCarrier object
		 instances). "
	   ::= {secondTransceiverPackage 2}

	basebandAdministrativeState-1	OBJECT-TYPE
	    SYNTAX	AdministrativeState
	    MAX-ACCESS	read-write
	    STATUS	current
	    DESCRIPTION
		"The semantics of the administrativeState attribute type are
		 specified in Recommendation X.731 and the syntax is defined
		 in Recommendation X.721.

		 This attribute has a value of locked(0), unlocked(1),
		 shuttingDown(2)."
	    REFERENCE
		"Owner Module: RRM module
		Mode-of-operation: set from manager
		Effective-time: immediatly"
	   ::= {secondTransceiverPackage 3}

	basebandAlarmStatus-1	OBJECT-TYPE
	    SYNTAX	AlarmStatus
	    MAX-ACCESS	read-write
	    STATUS	current
	    DESCRIPTION
		"The semantics and syntax of the alarmStatus attribute type
		 are specified in Recommendation M.3100.

		 This attribute has a value of underRepair(0), critical(1),
		 major(2), minor(3), alarmOutstanding(4)."
	    REFERENCE
		"Owner Module: RRM module
		Mode-of-operation: set from RRM
		Effective-time: immediatly"
	    ::= {secondTransceiverPackage 4}


	basebandOperationalState-1	OBJECT-TYPE
	    SYNTAX	OperationalState
	    MAX-ACCESS	read-write
	    STATUS	current
	    DESCRIPTION
		"The semantics of the operationalState attribute type is
		 specified in Recommendation X.731. A specification of the
		 syntax is found in Recommendation X.721.

		 This attribute has a value of disabled(0), enabled(1)."
	    REFERENCE
		"Owner Module: RRM module
		Mode-of-operation: set from RRM
		Effective-time: immediatly"
	   ::= {secondTransceiverPackage 5}

--	ViperCell	Channel Package
--
--	Note: There are 2 trx's on a viper cell, each with 8 channels.
--	Thus, this table was folded into the First and Second transceiver
--	data tables.
--
--
-- channelPackage OBJECT IDENTIFIER
-- 	DESCRIPTION
-- 		"The channel object class represents the manageable
-- 		 properties of a time slot. See Specification GSM 05.02
-- 		 for details. This package provides attributes for
-- 		 identification and management of the properties of the
-- 		 channel. A channel may or may not use frequency hopping.
-- 		 The usage of frequency hopping is indicated by the
-- 		 attribute frequencyUsage.
-- 
-- 		 The administrative states of the channel object have the
-- 		 following meanings: When a channel is locked it will
-- 		 immediately stop transmitting or receiving any information
-- 		 in the time slot. If the channel is a control channel, all
-- 		 calls in the BTS may be affected. When a channel is unlocked,
-- 		 it is able to accept traffic. When a channel is shutting down,
-- 		 no new traffic is allowed, no inbound handovers are accepted.
-- 		 In this state, clearing of existing traffic results in
-- 		 transition to locked state. The locked administrative state
-- 		 stops normal operations of the resource (not, for example,
-- 		 operations for test purposes)."
--	::= {gp10GsmMib 10}

	channel-1-Table	OBJECT-TYPE
	    SYNTAX	SEQUENCE OF Channel-1-Entry
	    MAX-ACCESS	not-accessible
	    STATUS	current
	    DESCRIPTION
		"This entry is required to define a table of values."
	    REFERENCE
		"Owner Module: RRM module
		Mode-of-operation: set from manager
		Effective-time: next restart"
	    ::= {secondTransceiverPackage 6}

	channel-1-Entry	OBJECT-TYPE
	    SYNTAX	Channel-1-Entry
	    MAX-ACCESS	not-accessible
	    STATUS	current
	    DESCRIPTION
		"This attribute defines the set of radio frequencies
		 allocated  and available to a cell. The first element
		 sets the BCCH frequency."
	    REFERENCE
		"Owner Module: RRM module
		Mode-of-operation: set from manager
		Effective-time: next restart"
	    INDEX	{channelIndex-1}
	    --DEFAULT cookie MIBT_%n
	    ::= {channel-1-Table 1}

	Channel-1-Entry	::= SEQUENCE {
	    channelIndex-1		 INTEGER,
	    channelID-1			 ChannelID,
	    channelCombination-1	 ChannelCombination,
	    channelFrequencyUsage-1	 FrequencyUsage,
	    channelTsc-1		 Tsc,
	    channelAdministrativeState-1 AdministrativeState,
	    channelOperationalState-1	 OperationalState
	}

	channelIndex-1	OBJECT-TYPE
	    SYNTAX	INTEGER (0..7)
	    MAX-ACCESS	read-only
	    STATUS	current
	    DESCRIPTION
		"This attribute is used as the index to this table. It
		 is a sequential number between 0 and 15."
	    REFERENCE
		"Owner Module: RRM module
		Mode-of-operation: set from manager
		Effective-time: next restart"
	    ::= {channel-1-Entry 1}

	channelID-1	OBJECT-TYPE
	    SYNTAX	ChannelID
	    MAX-ACCESS	read-write
	    STATUS	current
	    DESCRIPTION
		"This attribute is used for naming channel object
		 instances, and corresponds to the channel's time
		 slot number."
	    REFERENCE
		"Owner Module: RRM module
		 Mode-of-operation: set from manager
		 Effective-time: on restart"
	    ::= {channel-1-Entry 2}

	channelCombination-1	OBJECT-TYPE
	    SYNTAX	ChannelCombination
	    MAX-ACCESS	read-write
	    STATUS	current
	    DESCRIPTION
		"This attribute defines the logical channel combination
		 mapped onto the physical channel (time slot). For details
		 Refer to Specification GSM 05.02.

		 The following are the permitted ways, as defined by
		 GSM 04.03, in which channels can be combined onto basic
		 physical channels (numbers appearing in parenthesis after
		 channel designations indicate sub-channel numbers; channels
		 and sub-channels need not necessarily be assigned) :

		 i)	TCH/F + FACCH/F + SACCH/F
		 ii)	TCH/H(0,1) + FACCH/H(0,1) + SACCH/H(0,1)
		 iii)	TCH/H(0,0) + FACCH/H(0,1) + SACCH/H(0,1) + TCH/H(1,1)
		 iv)	FCCH + SCH + BCCH + CCCH
		 v)	FCCH + SCH + BCCH + CCCH + SDCCH/4(0...3) +  SACCH/C4(0...3)
		 vi)	BCCH + CCCH
		 vii)	SDCCH/8(0 ..7) + SACCH/C8(0 .. 7)
			where CCCH = PCH + RACH + AGCH 

		 Note 1: Where the SMSCB is supported, the CBCH replaces
			 SDCCH number 2 in cases v) and vii) above.
		 Note 2: A combined CCCH/SDCCH allocation (case v) above)
			 may only be used when no other CCCH channel is
			 allocated.

		 *********************************************************************
		 WARNING: Currently(Ver 1.5, 2.0 and 3.0) the only valid value of 
			 Channel Combination is TCHFull(0).
		 *********************************************************************"
	    REFERENCE
		"Owner Module: RRM module
		 Mode-of-operation: set from manager (only between combination I and V)
		 Effective-time: on restart"
	    ::= {channel-1-Entry 3}

	channelFrequencyUsage-1	OBJECT-TYPE
	    SYNTAX	FrequencyUsage
	    MAX-ACCESS	read-write
	    STATUS	current
	    DESCRIPTION
		"This attribute defines the frequencies used by a radio time
		 slot. If no frequency hopping is used, the attribute contains
		 an Absolute Radio Frequency Channel Number (ARFCN). If the
		 channel is configured to BCCH usage, the BCCH frequency is
		 set using the first value from the cellAllocation attribute
		 in the btsBasicPackage and the frequencyUsage attribute value
		 is ignored. If frequency hopping is used, the attribute
		 contains a reference to a frequencyHoppingSystem instance
		 plus the MAIO. ****"
	    REFERENCE
		"Owner Module: RRM module
		 Mode-of-operation: set from manager
		 Effective-time: on restart"
	    ::= {channel-1-Entry 4}

	channelTsc-1	OBJECT-TYPE
	    SYNTAX	Tsc
	    MAX-ACCESS	read-write
	    STATUS	current
	    DESCRIPTION
		"This attribute contains the Training Sequence Code (TSC)
		 of a radio channel. For control channels, TSC is always
		 equal to the BCC (Base Station Colour Code). For other
		 channels, there are no restrictions.

		 *********************************************************************
		 WARNING: Currently(Ver 1.5, 2.0 and 3.0) the only valid value of 
			 this variable is 0(Use BCC).
		 *********************************************************************"
	    REFERENCE
		"Owner Module: RRM module
		 Mode-of-operation: set from manager
		 Effective-time: immediately"
	    ::= {channel-1-Entry 5}

	channelAdministrativeState-1	OBJECT-TYPE
	    SYNTAX	AdministrativeState
	    MAX-ACCESS	read-write
	    STATUS	current
	    DESCRIPTION
		"The semantics of the administrativeState attribute type are
		 specified in Recommendation X.731 and the syntax is defined
		 in Recommendation X.721.

		 This attribute has a value of locked(0), unlocked(1),
		 shuttingDown(2)."
	    REFERENCE
		"Owner Module: RRM module
		 Mode-of-operation: set from manager
		 Effective-time: immediately"
	   ::= {channel-1-Entry 6}

	channelOperationalState-1	OBJECT-TYPE
	    SYNTAX	OperationalState
	    MAX-ACCESS	read-write
	    STATUS	current
	    DESCRIPTION
		"The semantics of the operationalState attribute type is
		 specified in Recommendation X.731. A specification of the
		 syntax is found in Recommendation X.721.

		 This attribute has a value of disabled(0), enabled(1)."
	    REFERENCE
		"Owner Module: RRM module
		 Mode-of-operation: set from RRM
		 Effective-time: on restart"
	   ::= {channel-1-Entry 7}

firstRadioCarrierPackage OBJECT IDENTIFIER
-- 	DESCRIPTION
-- 		"The radioCarrier managed object class is a functional
-- 		 entity representing the manageable properties of a radio
-- 		 carrier. Together with the basebandTransceiver and channel
-- 		 MOCs, it is meant to accommodate various system architectures
-- 		 including fixed frequency, baseband hopping, and synthesized
-- 		 hopping systems.
-- 
-- 		 This definition covers what may be described as the radio
-- 		 aspects of transmission in the GSM/DCS 1800 base station
-- 		 systems. This functionality is related to the baseband
-- 		 aspects by means of the associated channel definitions (see
-- 		 channel managed object class). This package provides the
-- 		 basic identification, control, and relationship attributes." 
	::= {gp10GsmMib 5}

	carrierFrequency-0-Table	OBJECT-TYPE
	    SYNTAX	SEQUENCE OF CarrierFrequency-0-Entry
	    MAX-ACCESS	not-accessible
	    STATUS	current
	    DESCRIPTION
		"This entry is required to define a table of values."
	    REFERENCE
		"Owner Module: RRM module
		 Mode-of-operation: set from manager
		 Effective-time: next restart"
	    ::= {firstRadioCarrierPackage 1}

	carrierFrequency-0-Entry	OBJECT-TYPE
	    SYNTAX	CarrierFrequency-0-Entry
	    MAX-ACCESS	not-accessible
	    STATUS	current
	    DESCRIPTION
		"This attribute is used to assign a set of (possibly one)
		 constant radio frequencies to a radioCarrier object. In
		 a fixed frequency or baseband hopping system, the set
		 will contain only one single frequency. In case of a
		 synthesizer hopping system, the set will contain all
		 frequencies the carrier is allowed to use. This set of
		 radio frequencies must be included in the allowed radio
		 frequency values specified by the cellAllocation attribute
		 of the containing bts object instance."
	    REFERENCE
		"Owner Module: RRM module
		 Mode-of-operation: set from manager
		 Effective-time: next restart"
	    INDEX	{carrierFrequencyIndex-0}
	    --DEFAULT cookie MIBT_%n
	    ::= {carrierFrequency-0-Table 1}

	CarrierFrequency-0-Entry	::= SEQUENCE {
	    carrierFrequencyIndex-0	INTEGER,
	    carrierFrequency-0		AbsoluteRFChannelNo
	}

	carrierFrequencyIndex-0	OBJECT-TYPE
	    SYNTAX	INTEGER
	    MAX-ACCESS	read-only
	    STATUS	current
	    DESCRIPTION
		"Index to the Carrier Frequency List."
	    REFERENCE
		"Owner Module: RRM module
		 Mode-of-operation: set from manager
		 Effective-time: next restart"
	    ::= {carrierFrequency-0-Entry 1}

	carrierFrequency-0	OBJECT-TYPE
	    SYNTAX	AbsoluteRFChannelNo
	    MAX-ACCESS	read-write
	    STATUS	current
	    DESCRIPTION
		"This attribute contains a radio frequency that is allocated
		 and available to this cell."
	    REFERENCE
		"Owner Module: RRM module
		 Mode-of-operation: set from manager
		 Effective-time: next restart"
	    ::= {carrierFrequency-0-Entry 2}

	powerClass-0	OBJECT-TYPE
	    SYNTAX	PowerClass
	    MAX-ACCESS	read-write
	    STATUS	current
	    DESCRIPTION
		"This attribute indicates the power class (max peak power)
		 of the transmitter. For further details refer to
		 Specification GSM 05.05."
	    REFERENCE
		"Owner Module: RRM module
		 Mode-of-operation: set from manager
		 Effective-time: next restart"
	    ::= {firstRadioCarrierPackage 2 }

	radioCarrierID-0	OBJECT-TYPE
	    SYNTAX	GSMGeneralObjectID
	    MAX-ACCESS	read-write
	    STATUS	current
	    DESCRIPTION
		"This attribute names a radioCarrier instance."
	    REFERENCE
		"Owner Module: RRM module
		 Mode-of-operation: set from manager
		 Effective-time: next restart"
	    ::= {firstRadioCarrierPackage 3}

	txPwrMaxReduction-0	OBJECT-TYPE
	    SYNTAX	TxPwrMaxReduction
	    MAX-ACCESS	read-write
	    STATUS	current
	    DESCRIPTION
		"This attribute specifies the number of 2 dB steps the
		 TX should be reduced from the maximum transmit power,
		 for tuning the cell coverage. The resulting attenuated
		 transmit power is the maximum nominal power Pn. See
		 Specifications GSM 05.05, GSM 05.08, and 08.58."
	    REFERENCE
		"Owner Module: RRM module
		 Mode-of-operation: set from manager
		 Effective-time: next restart"
	    ::= {firstRadioCarrierPackage 4}

	carrier-administrativeState-0	OBJECT-TYPE
	    SYNTAX	AdministrativeState
	    MAX-ACCESS	read-write
	    STATUS	current
	    DESCRIPTION
		"The semantics of the administrativeState attribute type are
		 specified in Recommendation X.731 and the syntax is defined
		 in Recommendation X.721.

		 This attribute has a value of locked(0), unlocked(1),
		 shuttingDown(2)."
	    REFERENCE
		"Owner Module: RRM module
		 Mode-of-operation: set from manager
		 Effective-time: immediately"
	    ::= {firstRadioCarrierPackage 5}

	carrier-alarmStatus-0	OBJECT-TYPE
	    SYNTAX	AlarmStatus
	    MAX-ACCESS	read-write
	    STATUS	current
	    DESCRIPTION
		"The semantics and syntax of the alarmStatus attribute type
		 are specified in Recommendation M.3100.

		 This attribute has a value of underRepair(0), critical(1),
		 major(2), minor(3), alarmOutstanding(4)."
	    REFERENCE
		"Owner Module: RRM module
		 Mode-of-operation: set from RRM
		 Effective-time: immediately"
	    ::= {firstRadioCarrierPackage 6}

	carrier-operationalState-0	OBJECT-TYPE
	    SYNTAX	OperationalState
	    MAX-ACCESS	read-write
	    STATUS	current
	    DESCRIPTION
		"The semantics of the operationalState attribute type is
		 specified in Recommendation X.731. A specification of the
		 syntax is found in Recommendation X.721.

		 This attribute has a value of disabled(0), enabled(1)."
	    REFERENCE
		"Owner Module: RRM module
		 Mode-of-operation: set from RRM
		 Effective-time: immediately"
	    ::= {firstRadioCarrierPackage 7}

secondRadioCarrierPackage OBJECT IDENTIFIER
-- 	DESCRIPTION
-- 		"The radioCarrier managed object class is a functional
-- 		 entity representing the manageable properties of a radio
-- 		 carrier. Together with the basebandTransceiver and channel
-- 		 MOCs, it is meant to accommodate various system architectures
-- 		 including fixed frequency, baseband hopping, and synthesized
-- 		 hopping systems.
-- 
-- 		 This definition covers what may be described as the radio
-- 		 aspects of transmission in the GSM/DCS 1800 base station
-- 		 systems. This functionality is related to the baseband
-- 		 aspects by means of the associated channel definitions (see
-- 		 channel managed object class). This package provides the
-- 		 basic identification, control, and relationship attributes." 
	::= {gp10GsmMib 6}

	carrierFrequency-1-Table	OBJECT-TYPE
	    SYNTAX	SEQUENCE OF CarrierFrequency-1-Entry
	    MAX-ACCESS	not-accessible
	    STATUS	current
	    DESCRIPTION
		"This entry is required to define a table of values."
	    REFERENCE
		"Owner Module: RRM module
		 Mode-of-operation: set from manager
		 Effective-time: next restart"
	    ::= {secondRadioCarrierPackage 1}

	carrierFrequency-1-Entry	OBJECT-TYPE
	    SYNTAX	CarrierFrequency-1-Entry
	    MAX-ACCESS	not-accessible
	    STATUS	current
	    DESCRIPTION
		"This attribute is used to assign a set of (possibly one)
		 constant radio frequencies to a radioCarrier object. In
		 a fixed frequency or baseband hopping system, the set
		 will contain only one single frequency. In case of a
		 synthesizer hopping system, the set will contain all
		 frequencies the carrier is allowed to use. This set of
		 radio frequencies must be included in the allowed radio
		 frequency values specified by the cellAllocation attribute
		 of the containing bts object instance."
	    REFERENCE
		"Owner Module: RRM module
		 Mode-of-operation: set from manager
		 Effective-time: next restart"
	    INDEX	{carrierFrequencyIndex-1}
	    --DEFAULT cookie MIBT_%n
	    ::= {carrierFrequency-1-Table 1}

	CarrierFrequency-1-Entry	::= SEQUENCE {
	    carrierFrequencyIndex-1	INTEGER,
	    carrierFrequency-1		AbsoluteRFChannelNo
	}

	carrierFrequencyIndex-1	OBJECT-TYPE
	    SYNTAX	INTEGER
	    MAX-ACCESS	read-only
	    STATUS	current
	    DESCRIPTION
		"Index to the Carrier Frequency List."
	    REFERENCE
		"Owner Module: RRM module
		 Mode-of-operation: set from manager
		 Effective-time: next restart"
	    ::= {carrierFrequency-1-Entry 1}

	carrierFrequency-1	OBJECT-TYPE
	    SYNTAX	AbsoluteRFChannelNo
	    MAX-ACCESS	read-write
	    STATUS	current
	    DESCRIPTION
		"This attribute contains a radio frequency that is allocated
		 and available to this cell."
	    REFERENCE
		"Owner Module: RRM module
		 Mode-of-operation: set from manager
		 Effective-time: next restart"
	    ::= {carrierFrequency-1-Entry 2}

	powerClass-1	OBJECT-TYPE
	    SYNTAX	PowerClass
	    MAX-ACCESS	read-write
	    STATUS	current
	    DESCRIPTION
		"This attribute indicates the power class (max peak power)
		 of the transmitter. For further details refer to
		 Specification GSM 05.05."
	    REFERENCE
		"Owner Module: RRM module
		 Mode-of-operation: set from manager
		 Effective-time: next restart"
	    ::= {secondRadioCarrierPackage 2 }

	radioCarrierID-1	OBJECT-TYPE
	    SYNTAX	GSMGeneralObjectID
	    MAX-ACCESS	read-write
	    STATUS	current
	    DESCRIPTION
		"This attribute names a radioCarrier instance."
	    REFERENCE
		"Owner Module: RRM module
		 Mode-of-operation: set from manager
		 Effective-time: next restart"
	    ::= {secondRadioCarrierPackage 3 }

	txPwrMaxReduction-1	OBJECT-TYPE
	    SYNTAX	TxPwrMaxReduction
	    MAX-ACCESS	read-write
	    STATUS	current
	    DESCRIPTION
		"This attribute specifies the number of 2 dB steps the
		 TX should be reduced from the maximum transmit power,
		 for tuning the cell coverage. The resulting attenuated
		 transmit power is the maximum nominal power Pn. See
		 Specifications GSM 05.05, GSM 05.08, and 08.58."
	    REFERENCE
		"Owner Module: RRM module
		 Mode-of-operation: set from manager
		 Effective-time: next restart"
	    ::= {secondRadioCarrierPackage 4}

	carrier-administrativeState-1	OBJECT-TYPE
	    SYNTAX	AdministrativeState
	    MAX-ACCESS	read-write
	    STATUS	current
	    DESCRIPTION
		"The semantics of the administrativeState attribute type are
		 specified in Recommendation X.731 and the syntax is defined
		 in Recommendation X.721.

		 This attribute has a value of locked(0), unlocked(1),
		 shuttingDown(2)."
	    REFERENCE
		"Owner Module: RRM module
		 Mode-of-operation: set from manager
		 Effective-time: immediately"
	    ::= {secondRadioCarrierPackage 5}

	carrier-alarmStatus-1	OBJECT-TYPE
	    SYNTAX	AlarmStatus
	    MAX-ACCESS	read-write
	    STATUS	current
	    DESCRIPTION
		"The semantics and syntax of the alarmStatus attribute type
		 are specified in Recommendation M.3100.

		 This attribute has a value of underRepair(0), critical(1),
		 major(2), minor(3), alarmOutstanding(4)."
	    REFERENCE
		"Owner Module: RRM module
		 Mode-of-operation: set from RRM
		 Effective-time: immediately"
	    ::= {secondRadioCarrierPackage 6}

	carrier-operationalState-1	OBJECT-TYPE
	    SYNTAX	OperationalState
	    MAX-ACCESS	read-write
	    STATUS	current
	    DESCRIPTION
		"The semantics of the operationalState attribute type is
		 specified in Recommendation X.731. A specification of the
		 syntax is found in Recommendation X.721.

		 This attribute has a value of disabled(0), enabled(1)."
	    REFERENCE
		"Owner Module: RRM module
		 Mode-of-operation: set from RRM
		 Effective-time: immediately"
	    ::= {secondRadioCarrierPackage 7}

btsTimerPackage OBJECT IDENTIFIER
-- 	DESCRIPTION
-- 		"This package contains a set of timers used on layers
-- 		 2 and 3 of the air interface."
	::= {gp10GsmMib 7}

	t200 OBJECT IDENTIFIER
--	    SYNTAX	TimerStructure
--	    MAX-ACCESS	not-accessible
--	    DESCRIPTION
--		"This attribute contains values for the LapDm timer T200,
--		 to be used on the different control channels. See
--		 Specification GSM 04.06."
--	    REFERENCE
--		"Owner Module: LAPDM module
--		 Mode-of-operation: set from manager
--		 Effective-time: on next new call"
	    ::= { btsTimerPackage 1 }

	sdcchSAPI0	OBJECT-TYPE
	    SYNTAX	L2Timer
	    MAX-ACCESS	read-write
	    STATUS	current
	    DESCRIPTION
		"SDCCH, SAPI 0. Value is in 5 ms units."
	    REFERENCE
		"Owner Module: LAPDM module
		 Mode-of-operation: set from manager
		 Effective-time: on next new call"
	    ::= {t200 1}

	facchTCHF	OBJECT-TYPE
	    SYNTAX	L2Timer
	    MAX-ACCESS	read-write
	    STATUS	current
	    DESCRIPTION
		"associated with a full rate TCH. Value is in 5 ms units."
	    REFERENCE
		"Owner Module: LAPDM module
		 Mode-of-operation: set from manager
		 Effective-time: on next new call"
	    ::= {t200 2}

	facchTCHH	OBJECT-TYPE
	    SYNTAX	L2Timer
	    MAX-ACCESS	read-write
	    STATUS	current
	    DESCRIPTION
		"Associated with a half rate TCH. Value is in 5 ms units."
	    REFERENCE
		"Owner Module: LAPDM module
		 Mode-of-operation: set from manager
		 Effective-time: on next new call"
	    ::= {t200 3}

	sacchTCHSAPI0	OBJECT-TYPE
	    SYNTAX	L2Timer
	    MAX-ACCESS	read-write
	    STATUS	current
	    DESCRIPTION
		"SACCH with TCH, SAPI 0. Value is in 5 ms units."
	    REFERENCE
		"Owner Module: LAPDM module
		 Mode-of-operation: set from manager
		 Effective-time: on next new call"
	    ::= {t200 4}

	sacchSDCCH	OBJECT-TYPE
	    SYNTAX	L2Timer
	    MAX-ACCESS	read-write
	    STATUS	current
	    DESCRIPTION
		"SACCH with SDCCH. Value is in 5 ms units."
	    REFERENCE
		"Owner Module: LAPDM module
		 Mode-of-operation: set from manager
		 Effective-time: on next new call"
	    ::= {t200 5}

	sdcchSAPI3	OBJECT-TYPE
	    SYNTAX	L2Timer
	    MAX-ACCESS	read-write
	    STATUS	current
	    DESCRIPTION
		"SDCCH, SAPI 3. Value is in 5 ms units."
	    REFERENCE
		"Owner Module: LAPDM module
		 Mode-of-operation: set from manager
		 Effective-time: on next new call"
	    ::= {t200 6}

	sdcchTCHSAPI3	OBJECT-TYPE
	    SYNTAX	L2Timer
	    MAX-ACCESS	read-write
	    STATUS	current
	    DESCRIPTION
		"SDCCH with TCH, SAPI 3. Value is in 5 ms units."
	    REFERENCE
		"Owner Module: LAPDM module
		 Mode-of-operation: set from manager
		 Effective-time: on next new call"
	    ::= {t200 7}

	t31xx OBJECT IDENTIFIER
--	    SYNTAX	TimerStructure
--	    MAX-ACCESS	not-accessible
--	    DESCRIPTION
--		"This attribute contains the values of the set of timers
--		 used on the air interface. See Specification GSM 04.08
--		 for more details."
--	    REFERENCE
--		"Owner Module: RRM module, except t3113 for MM module
--		 Mode-of-operation: set from manager
--		 Effective-time: on next new call/paging"
	    ::= { btsTimerPackage 2 }

	t3101	OBJECT-TYPE
	    SYNTAX	L3Timer
	    MAX-ACCESS	read-write
	    STATUS	current
	    DESCRIPTION
		"used with IMMEDIATE ASSIGNMENT. Value is in 10 ms units."
	    REFERENCE
		"Owner Module: RRM module
		 Mode-of-operation: set from manager
		 Effective-time: on next new call/paging"
	    ::= {t31xx 1}

	t3103	OBJECT-TYPE
	    SYNTAX	L3Timer
	    MAX-ACCESS	read-write
	    STATUS	current
	    DESCRIPTION
		"used with HANDOVER COMMAND. Value is in 10 ms units."
	    REFERENCE
		"Owner Module: RRM module
		 Mode-of-operation: set from manager
		 Effective-time: on next new call/paging"
	    ::= {t31xx 2}

	t3105	OBJECT-TYPE
	    SYNTAX	L3Timer
	    MAX-ACCESS	read-write
	    STATUS	current
	    DESCRIPTION
		"used with PHYSICAL INFORMATION. Value is in 10 ms units."
	    REFERENCE
		"Owner Module: RRM module
		 Mode-of-operation: set from manager
		 Effective-time: on next new call/paging"
	    ::= {t31xx 3}

	t3107	OBJECT-TYPE
	    SYNTAX	L3Timer
	    MAX-ACCESS	read-write
	    STATUS	current
	    DESCRIPTION
		"used with ASSIGNMENT COMMAND. Value is in 10 ms units."
	    REFERENCE
		"Owner Module: RRM module
		 Mode-of-operation: set from manager
		 Effective-time: on next new call/paging"
	    ::= {t31xx 4}

	t3109	OBJECT-TYPE
	    SYNTAX	L3Timer
	    MAX-ACCESS	read-write
	    STATUS	current
	    DESCRIPTION
		"used for lower layer failures. Value is in 10 ms units."
	    REFERENCE
		"Owner Module: RRM module
		 Mode-of-operation: set from manager
		 Effective-time: on next new call/paging"
	    ::= {t31xx 5}

	t3111	OBJECT-TYPE
	    SYNTAX	L3Timer
	    MAX-ACCESS	read-write
	    STATUS	current
	    DESCRIPTION
		"used for channel activation delay. Value is in 10 ms units."
	    REFERENCE
		"Owner Module: RRM module
		 Mode-of-operation: set from manager
		 Effective-time: on next new call/paging"
	    ::= {t31xx 6}

	t3113	OBJECT-TYPE
	    SYNTAX	L3Timer
	    MAX-ACCESS	read-write
	    STATUS	current
	    DESCRIPTION
		"used with PAGING messages. Value is in 10 ms units."
	    REFERENCE
		"Owner Module: MM module
		 Mode-of-operation: set from manager
		 Effective-time: on next new call/paging"
	    ::= {t31xx 7}

--	Adjacent Cell Handover Package
--	Adjacent Cell Reselection Package

adjacentCellPackage OBJECT IDENTIFIER
-- 	DESCRIPTION
-- 		"The MOC adjacentCellHandOver, by means of this package,
-- 		contains handover related, adjacent cell specific, parameters
-- 		that are independent of any particular handover algorithm.
-- 
-- 		The MOC adjacentCellHandOver acts as a base class only.
-- 		Instances of it are never created. A handover algorithm
-- 		specific subclass, such as adjacentCellHandOverGSM0508 or a
-- 		manufacturer specific subclass of adjacentCellHandOver must
-- 		be instantiated for managing the parameters specific to that
-- 		particular handover algorithm.  The maximum number of adjacent
-- 		cells that may be used for handover is 32."
	::= {gp10GsmMib 8}

	adjCell-handoverTable	OBJECT-TYPE
	    SYNTAX	SEQUENCE OF AdjCell-handoverEntry
	    MAX-ACCESS	not-accessible
	    STATUS	current
	    DESCRIPTION
		"This entry is required to define a table of values."
	    REFERENCE
		"Owner Module: RRM module
		Mode-of-operation: set from manager
		Effective-time: next restart"
	    ::= {adjacentCellPackage 1}

	adjCell-handoverEntry	OBJECT-TYPE
	    SYNTAX	AdjCell-handoverEntry
	    MAX-ACCESS	not-accessible
	    STATUS	current
	    DESCRIPTION
		"This attribute defines the set of radio frequencies
		 allocated  and available to a cell. The first element
		 sets the BCCH frequency."
	    REFERENCE
		"Owner Module: RRM module
		Mode-of-operation: set from manager
		Effective-time: next restart"
	    INDEX	{adjCell-handoverIndex}
	    --DEFAULT cookie MIBT_%n
	    ::= {adjCell-handoverTable 1}

	AdjCell-handoverEntry	::= SEQUENCE {
	    adjCell-handoverIndex	INTEGER,
	    adjCell-handoverCellID	GSMGeneralObjectID,
	    adjCell-mcc			MobileCountryCode,
	    adjCell-mnc			MobileNetworkCode,
	    adjCell-lac			LocationAreaCode,
	    adjCell-ci			CellIdentity,
	    adjCell-bCCHFrequency	AbsoluteRFChannelNo,
	    adjCell-ncc			NetworkColourCode,
	    adjCell-cid			CellIdentity,
	    adjCell-synchronized	Boolean,
	    adjCell-hoPriorityLevel	HoPriorityLevel,
	    adjCell-hoMargin		HoMargin,
	    adjCell-msTxPwrMaxCell	TxPower,
	    adjCell-rxLevMinCell	RxLev,
		adjCell-isExternal		Boolean
	}

	adjCell-handoverIndex	OBJECT-TYPE
	    SYNTAX	INTEGER
	    MAX-ACCESS	read-only
	    STATUS	current
	    DESCRIPTION
		"This attribute is used for naming adjacent cell objects,
		i.e. instances of the classes adjacentCellHandOver and
		adjacentCellReselection, as well as their subclasses."
	    REFERENCE
		"Owner Module: HO-Signaling module
		Mode-of-operation: set from manager
		Effective-time: next restart"
	    ::= {adjCell-handoverEntry 1}

	adjCell-handoverCellID	OBJECT-TYPE
	    SYNTAX	GSMGeneralObjectID
	    MAX-ACCESS	read-write
	    STATUS	current
	    DESCRIPTION
		"This attribute is used for naming adjacent cell objects,
		i.e. instances of the classes adjacentCellHandOver and
		adjacentCellReselection, as well as their subclasses."
	    REFERENCE
		"Owner Module: HO-Signaling module
		Mode-of-operation: set from manager
		Effective-time: next restart"
	    ::= {adjCell-handoverEntry 2}

	adjCell-mcc	OBJECT-TYPE
	    SYNTAX	MobileCountryCode
	    MAX-ACCESS	read-write
	    STATUS	current
	    DESCRIPTION
		"This attribute contains the Cell Identification (CI) and
		the Location Area of the cell. A Location Area  is unique
		within a GSM PLMN; a Cell Identification is unique within
		a location area. For further details see Spec GSM 03.03.
		
		MobileCountryCode
		
		Note: 3 digit in decimal which is saved in INTEGER variable in BCD format
		     B[12..31]: 0(don't care)
		     B[8..11]:  1st digit(most significant digit), valid range 0 ~ 9
		     B[4..7]:   2nd digit, valid range 0 ~ 9
		     B[0..3]:   3rd digit(least significant digit), valid range 0 ~ 9
		"
	    REFERENCE
		"Owner Module: HO-Signaling module
		Mode-of-operation: set from manager
		Effective-time: next restart"
	    ::= {adjCell-handoverEntry 3}

	adjCell-mnc	OBJECT-TYPE
	    SYNTAX	MobileNetworkCode
	    MAX-ACCESS	read-write
	    STATUS	current
	    DESCRIPTION
		"Mobile Network Code
		
		Note: 2 or 3 digit in decimal which is saved in INTEGER variable in BCD format except last digit which may have 0xf
		     B[12..31]: 0(don't care)
		     B[8..11]:  1st digit(most significant digit), valid range 0 ~ 9
		     B[4..7]:   2nd digit, valid range 0 ~ 9
		     B[0..3]:   3rd digit(least significant digit), valid range 0 ~ 9 or 0xf
		     if last digit has 0xf, then MNC is 2 digit, else if it has 0 ~ 9 then MNC is 3 digit.
		"
	    REFERENCE
		"Owner Module: HO-Signaling module
		Mode-of-operation: set from manager
		Effective-time: next restart"
	    ::= {adjCell-handoverEntry 4}

	adjCell-lac	OBJECT-TYPE
	    SYNTAX	LocationAreaCode
	    MAX-ACCESS	read-write
	    STATUS	current
	    DESCRIPTION
		"Location Area Code"
	    REFERENCE
		"Owner Module: HO-Signaling module
		Mode-of-operation: set from manager
		Effective-time: next restart"
	    ::= {adjCell-handoverEntry 5}

	adjCell-ci	OBJECT-TYPE
	    SYNTAX	CellIdentity
	    MAX-ACCESS	read-write
	    STATUS	current
	    DESCRIPTION
		"Cell Identity Code"
	    REFERENCE
		"Owner Module: HO-Signaling module
		Mode-of-operation: set from manager
		Effective-time: next restart"
	    ::= {adjCell-handoverEntry 6}

	adjCell-bCCHFrequency	OBJECT-TYPE
	    SYNTAX	AbsoluteRFChannelNo
	    MAX-ACCESS	read-write
	    STATUS	current
	    DESCRIPTION
		"This attribute contains the absolute radio frequency channel
		number of the BCCH channel of adjacent cells. This information
		is sent to the mobile station." 
	    REFERENCE
		"Owner Module: HO-Signaling module
		Mode-of-operation: set from manager
		Effective-time: next restart"
	   ::= {adjCell-handoverEntry 7}

	adjCell-ncc	OBJECT-TYPE
	    SYNTAX	NetworkColourCode
	    MAX-ACCESS	read-write
	    STATUS	current
	    DESCRIPTION
		"This attribute contains the Base Station Identity Code (BSIC),
		which is transmitted on the SCH and used for identifying a BTS.
		The BSIC consists of the Network Colour Code (NCC) and the Base
		Station Colour Code (BCC). Refer to Specification GSM 04.08."
	    REFERENCE
		"Owner Module: HO-Signaling module
		Mode-of-operation: set from manager
		Effective-time: next restart"
	    ::= {adjCell-handoverEntry 8}

	adjCell-cid	OBJECT-TYPE
	    SYNTAX	CellIdentity
	    MAX-ACCESS	read-write
	    STATUS	current
	    DESCRIPTION
		"Mobile Network Code"
	    REFERENCE
		"Owner Module: HO-Signaling module
		Mode-of-operation: set from manager
		Effective-time: next restart"
	    ::= {adjCell-handoverEntry 9}

	adjCell-synchronized		OBJECT-TYPE
	    SYNTAX	Boolean
	    MAX-ACCESS	read-write
	    STATUS	current
	    DESCRIPTION
		"This attribute of the object class adjacentCellHandOver
		indicates whether the adjacent cell is synchronized with the
		origin cell. Refer to Specification GSM 05.08 (N_CELL_LIST).

		 *********************************************************************
		 WARNING: Currently(Ver 1.5, 2.0 and 3.0) the only valid value of 
			 adjCell-synchronized is 0(false).
		 *********************************************************************"
	    REFERENCE
		"Owner Module: HO-Signaling module
		Mode-of-operation: set from manager
		Effective-time: next restart"
	   ::= {adjCell-handoverEntry 10}

	adjCell-hoPriorityLevel	OBJECT-TYPE
	    SYNTAX	HoPriorityLevel
	    MAX-ACCESS	read-write
	    STATUS	current
	    DESCRIPTION
		"This attribute defines the handover priority level for an
		adjacent cell used for target cell evaluation in the handover
		control process. Eight distinct priority levels exist."
	    REFERENCE
		"Owner Module: HO-Signaling module
		Mode-of-operation: set from manager
		Effective-time: immediate"
	    ::= {adjCell-handoverEntry 11}

	adjCell-hoMargin	OBJECT-TYPE
	    SYNTAX	HoMargin
	    MAX-ACCESS	read-write
	    STATUS	current
	    DESCRIPTION
		"The value of this attribute is used as a threshold to prevent
		repetative hand-over between adjacent cells, in case the
		handover is caused by received signal level or the power
		budget process. Refer to Annex A of Specification GSM 05.08
		(HO_MARGIN (n))"
	    REFERENCE
		"Owner Module: HO-Signaling module
		Mode-of-operation: set from manager
		Effective-time: immediate"
	    ::= {adjCell-handoverEntry 12}

	adjCell-msTxPwrMaxCell	OBJECT-TYPE
	    SYNTAX	TxPower
	    MAX-ACCESS	read-write
	    STATUS	current
	    DESCRIPTION
		"This attribute specifies whether call priority is ASSIGNMENT
		REQUEST message (or HANDOVER REQUEST message in ho) from MSC
		is taken into account in queue handling"
	    REFERENCE
		"Owner Module: HO-Signaling module
		Mode-of-operation: set from manager
		Effective-time: immediate"
	    ::= {adjCell-handoverEntry 13}

	adjCell-rxLevMinCell	OBJECT-TYPE
	    SYNTAX	RxLev
	    MAX-ACCESS	read-write
	    STATUS	current
	    DESCRIPTION
		"This attribute holds the minimum received signal strength in
		a cell, for a MS to be handed over to that cell. See Annex A
		of Specification GSM 05.08 (RXLEV_MIN (n)). This is an
		attribute of the object class adjacentCellHandOverGSM0508;
		each adjacent cell may thus have a specific value."
	    REFERENCE
		"Owner Module: HO-Signaling module
		Mode-of-operation: set from manager
		Effective-time: immediate"
	    ::= {adjCell-handoverEntry 14}


	adjCell-isExternal	OBJECT-TYPE
	    SYNTAX		Boolean
	    MAX-ACCESS	read-write
	    STATUS	current
	    DESCRIPTION
		"This attribute specifies whether this row corresponds to an 
		 external cell (outside this MNET)."
	    ::= {adjCell-handoverEntry 15}


--	Adjacent Cell Reselection Package
--
--	To save on the Callback stubs in the SNMP manager, the Adjacent Cell
--	Reselection Package has been folded togeather with the Adjacent Cell
--	Handover Package.
--
-- adjacentCellReselectionPackage OBJECT IDENTIFIER
-- 	DESCRIPTION
-- 		"Instances of adjacentCellReselection may be created for
-- 		 representing an adjacent cell a MS may use for reselection,
-- 		 only. To represent an adjacent cell to which handovers are
-- 		 allowed, another MOC must be used (see MOCs adjacentCellHandOver,
-- 		 adjacentCellHandOverGSM0508 and adjacentCellHandOverGSM0508AndReselection).
-- 		 The maximum number of adjacent cells that may be used for
-- 		 reselection is 32. This package contains the attributes
-- 		 necessary to identify the cell."

	adjCell-reselectionTable	OBJECT-TYPE
	    SYNTAX	SEQUENCE OF AdjCell-ReselectionEntry
	    MAX-ACCESS	not-accessible
	    STATUS	current
	    DESCRIPTION
		"This entry is required to define a table of values."
	    REFERENCE
		"Owner Module: RRM module
		Mode-of-operation: set from manager
		Effective-time: next restart"
	    ::= {adjacentCellPackage 2}

	adjCell-reselectionEntry	OBJECT-TYPE
	    SYNTAX	AdjCell-ReselectionEntry
	    MAX-ACCESS	not-accessible
	    STATUS	current
	    DESCRIPTION
		"This attribute defines the set of radio frequencies
		 allocated  and available to a cell. The first element
		 sets the BCCH frequency."
	    REFERENCE
		"Owner Module: RRM module
		Mode-of-operation: set from manager
		Effective-time: next restart"
	    INDEX	{adjCell-reselectionIndex}
	    --DEFAULT cookie MIBT_%n
	    ::= {adjCell-reselectionTable 1}

	AdjCell-ReselectionEntry	::= SEQUENCE {
	    adjCell-reselectionIndex		INTEGER,
	    adjCell-reselectionCellID		GSMGeneralObjectID,
	    adjCell-reselectionBCCHFrequency	AbsoluteRFChannelNo
	}

	adjCell-reselectionIndex	OBJECT-TYPE
	    SYNTAX	INTEGER (0..31)
	    MAX-ACCESS	read-only
	    STATUS	current
	    DESCRIPTION
		"This attribute is used as the index to this table. It
		 is a sequential number between 0 and 31."
	    REFERENCE
		"Owner Module: RRM module
		Mode-of-operation: set from manager
		Effective-time: next restart"
	    ::= {adjCell-reselectionEntry 1}

	adjCell-reselectionCellID	OBJECT-TYPE
	    SYNTAX	GSMGeneralObjectID
	    MAX-ACCESS	read-write
	    STATUS	current
	    DESCRIPTION
		"This attribute is used for naming adjacent cell objects,
		i.e. instances of the classes adjCell-HandOver and
		adjCell-reselection, as well as their subclasses."
	    REFERENCE
		"Owner Module: RRM module
		Mode-of-operation: set from manager
		Effective-time: next restart"
	    ::= {adjCell-reselectionEntry 2}


	adjCell-reselectionBCCHFrequency	OBJECT-TYPE
	    SYNTAX	AbsoluteRFChannelNo
	    MAX-ACCESS	read-write
	    STATUS	current
	    DESCRIPTION
		"This attribute contains the absolute radio frequency channel
		number of the BCCH channel of adjacent cells. This information
		is sent to the mobile station." 
	    REFERENCE
		"Owner Module: RRM module
		Mode-of-operation: set from manager
		Effective-time: next restart"
	   ::= {adjCell-reselectionEntry 3}

frequencyHoppingPackage OBJECT IDENTIFIER
-- 	DESCRIPTION
-- 		"The frequencyHopping object class represents a set
-- 		 of radio frequency channels used in a specific frequency
-- 		 hopping sequence. An instance of frequencyHopping
-- 		 may be (and often is) shared by one or more channels.
-- 		 This package provides identification and the basic
-- 		 attributes for configuring the hopping system."
	::= {gp10GsmMib 9}

	frequencyHoppingSystemID	OBJECT-TYPE
	    SYNTAX	GSMGeneralObjectID
	    MAX-ACCESS	read-write
	    STATUS	current
	    DESCRIPTION
		"This attribute names a frequencyHopping instance."
	    REFERENCE
		"Owner Module: FH module
		 Mode-of-operation: set from manager
		 Effective-time: on restart"
	    ::= {frequencyHoppingPackage 1}

	hoppingSequenceNumber	OBJECT-TYPE
	    SYNTAX	HoppingSequenceNumber
	    MAX-ACCESS	read-write
	    STATUS	current
	    DESCRIPTION
		"The Hopping Sequence Number (HSN) determines the order
		 in which the allocated frequencies are used.  Refer to
		 Specification GSM 05.02."
	    REFERENCE
		"Owner Module: FH module
		 Mode-of-operation: set from manager
		 Effective-time: on restart"
	   ::= {frequencyHoppingPackage 2}

	mobileAllocationTable	OBJECT-TYPE
	    SYNTAX	SEQUENCE OF MobileAllocationEntry
	    MAX-ACCESS	not-accessible
	    STATUS	current
	    DESCRIPTION
		"The attribute mobileAllocation specifies the set of radio
		 frequencies (ARFCNs) allocated to all channels that belong
		 to the frequencyHopping instance that contains the
		 attribute. This set of radio frequencies must be included
		 in the allowed radio frequency values specified by the
		 cellAllocation attribute of the containing bts object
		 instance."
	    REFERENCE
		"Owner Module: FH module
		 Mode-of-operation: set from manager
		 Effective-time: on restart"
	    ::= {frequencyHoppingPackage 3}

	mobileAllocationEntry	OBJECT-TYPE
	    SYNTAX	MobileAllocationEntry
	    MAX-ACCESS	not-accessible
	    STATUS	current
	    DESCRIPTION
		"This entry is required to define a table of values."
	    REFERENCE
		"Owner Module: FH module
		 Mode-of-operation: set from manager
		 Effective-time: on restart"
	    INDEX	{mobileAllocationIndex}
	    --DEFAULT cookie MIBT_%n
	    ::= {mobileAllocationTable 1}

	MobileAllocationEntry	::= SEQUENCE {
	    mobileAllocationIndex	INTEGER,
	    mobileAllocation		AbsoluteRFChannelNo
	}

	mobileAllocationIndex	OBJECT-TYPE
	    SYNTAX	INTEGER
	    MAX-ACCESS	read-only
	    STATUS	current
	    DESCRIPTION
		"Index to the Mobile Allocation table."
	    REFERENCE
		"Owner Module: FH module
		 Mode-of-operation: set from manager
		 Effective-time: on restart"
	    ::= {mobileAllocationEntry 1}

	mobileAllocation	OBJECT-TYPE
	    SYNTAX	AbsoluteRFChannelNo
	    MAX-ACCESS	read-write
	    STATUS	current
	    DESCRIPTION
		"The attribute mobileAllocation specifies the set of radio
		 frequencies (ARFCNs) allocated to all channels that belong
		 to the frequencyHopping instance that contains the
		 attribute. This set of radio frequencies must be included
		 in the allowed radio frequency values specified by the
		 cellAllocation attribute of the containing bts object
		 instance."
	    REFERENCE
		"Owner Module: FH module
		 Mode-of-operation: set from manager
		 Effective-time: on restart"
	    ::= {mobileAllocationEntry 2}

handoverControlPackage OBJECT IDENTIFIER
-- 	DESCRIPTION
-- 		"The object class handoverControlGSM0508, by means of this
-- 		 package, contains the parameters of the default handover
-- 		 algorithm defined in Annex A of Specification GSM 05.08.
-- 		 This class may be used, if the BSS supports the default
-- 		 handover algorithm."
	::= {gp10GsmMib 10}

	handoverControlID	OBJECT-TYPE
	    SYNTAX	GSMGeneralObjectID
	    MAX-ACCESS	read-write
	    STATUS	current
	    DESCRIPTION
		"This attribute names an instance of the object class
		 handoverControl."
	    REFERENCE
		"Owner Module: HO-signaling module
		 Mode-of-operation: set from manager
		 Effective-time: next restart"
	    ::= {handoverControlPackage 1}

	enableOptHandoverProcessing	OBJECT-TYPE
	    SYNTAX	EnableHoType
	    MAX-ACCESS	read-write
	    STATUS	current
	    DESCRIPTION
		"The attribute specifies the allowed optional handover
		 processing as specified in GSM 05.08 Annex A. The
		 following handover processing options exist:

		 - power budget
		 - MS distance."
	    REFERENCE
		"Owner Module: HO-algorithm module in L1
		 Mode-of-operation: set from manager
		 Effective-time: immediately"
	    ::= {handoverControlPackage 2}

	hoAveragingAdjCellParam	OBJECT IDENTIFIER
--	    SYNTAX	SubStructure
--	    MAX-ACCESS	not-accessible
--	    DESCRIPTION
--		"This attribute contains averaging parameters used for
--		 averaging signal level measurements from adjacent cells
--		 (GSM 05.08 - RXLEV_NCELL(n)).
--
--		 -	The number of SACCH multiframes over which results are
--		 	averaged, i.e. the window size (Hreqave in GSM 05.08).
--		 -	The number of results sent in the 'handover required'
--			message (Hreqt in GSM 05.08).
--		 -	Weighting"
--	    REFERENCE
--		"Owner Module: HO-algorithm module in L1
--		 Mode-of-operation: set from manager
--		 Effective-time: immediately"
	    ::= {handoverControlPackage 3}

	hoAveragingAdjCellParamHreqave	OBJECT-TYPE
	    SYNTAX	AveragingNumber
	    MAX-ACCESS	read-write
	    STATUS	current
	    DESCRIPTION
		"Refer to GSM 05.08 (Hreqave)"
	    REFERENCE
		"Owner Module: HO-algorithm module in L1
		 Mode-of-operation: set from manager
		 Effective-time: immediately"
	    ::= {hoAveragingAdjCellParam 1}

	hoAveragingAdjCellParamHreqt	OBJECT-TYPE
	    SYNTAX	AveragingNumber
	    MAX-ACCESS	read-write
	    STATUS	current
	    DESCRIPTION
		"Refer to GSM 05.08 (Hreqt)"
	    REFERENCE
		"Owner Module: HO-algorithm module in L1
		 Mode-of-operation: set from manager
		 Effective-time: immediately"
	    ::= {hoAveragingAdjCellParam 2}

	hoAveragingAdjCellParamWeighting	OBJECT-TYPE
	    SYNTAX	Weighting
	    MAX-ACCESS	read-write
	    STATUS	current
	    DESCRIPTION
		"Weighting value (0..3)"
	    REFERENCE
		"Owner Module: HO-algorithm module in L1
		 Mode-of-operation: set from manager
		 Effective-time: immediately"
	    ::= {hoAveragingAdjCellParam 3}

	hoAveragingDistParam	OBJECT IDENTIFIER
--	    SYNTAX	SubStructure
--	    MAX-ACCESS	not-accessible
--	    DESCRIPTION
--		"The hoAveragingDistParam attribute contains averaging
--		 parameters used in the handover process, in case the
--		 handover cause is distance between the Mobile Station
--		 and the BTS. See Specification GSM 05.08.
--
--		 -	The number of SACCH multiframes over which results
--		 	are averaged, i.e. the window size (Hreqave).
--		 -	The number of results sent in the 'handover required'
--			message (Hreqt). "
--	    REFERENCE
--		"Owner Module: HO-algorithm module in L1
--		 Mode-of-operation: set from manager
--		 Effective-time: immediately"
	    ::= {handoverControlPackage 4}

	hoAveragingDistParamHreqave	OBJECT-TYPE
	    SYNTAX	AveragingNumber
	    MAX-ACCESS	read-write
	    STATUS	current
	    DESCRIPTION
		"Refer to GSM 05.08 (Hreqave)"
	    REFERENCE
		"Owner Module: HO-algorithm module in L1
		 Mode-of-operation: set from manager
		 Effective-time: immediately"
	    ::= {hoAveragingDistParam 1}

	hoAveragingDistParamHreqt	OBJECT-TYPE
	    SYNTAX	AveragingNumber
	    MAX-ACCESS	read-write
	    STATUS	current
	    DESCRIPTION
		"Refer to GSM 05.08 (Hreqt)"
	    REFERENCE
		"Owner Module: HO-algorithm module in L1
		 Mode-of-operation: set from manager
		 Effective-time: immediately"
	    ::= {hoAveragingDistParam 2}

	hoAveragingLevParam	OBJECT IDENTIFIER
--	    SYNTAX	SubStructure
--	    MAX-ACCESS	not-accessible
--	    DESCRIPTION
--		"The hoAveragingLevParam attribute contains averaging
--		 parameters for the signal strength measurements.
--		 -	The number of SACCH multiframes over which
--		 	results are averaged, i.e. the window size
--			(Hreqave in GSM 05.08).
--		-	The number of results sent in the 'handover
--			required' message (Hreqt in GSM 05.08).
--		-	Weighting"
--	    REFERENCE
--		"Owner Module: HO-algorithm module in L1
--		 Mode-of-operation: set from manager
--		 Effective-time: immediately"
	    ::= {handoverControlPackage 5}

	hoAveragingLevParamHreqave	OBJECT-TYPE
	    SYNTAX	AveragingNumber
	    MAX-ACCESS	read-write
	    STATUS	current
	    DESCRIPTION
		"Refer to GSM 05.08 (Hreqave)"
	    REFERENCE
		"Owner Module: HO-algorithm module in L1
		 Mode-of-operation: set from manager
		 Effective-time: immediately"
	    ::= {hoAveragingLevParam 1}

	hoAveragingLevParamHreqt	OBJECT-TYPE
	    SYNTAX	AveragingNumber
	    MAX-ACCESS	read-write
	    STATUS	current
	    DESCRIPTION
		"Refer to GSM 05.08 (Hreqt)"
	    REFERENCE
		"Owner Module: HO-algorithm module in L1
		 Mode-of-operation: set from manager
		 Effective-time: immediately"
	    ::= {hoAveragingLevParam 2}

	hoAveragingLevParamWeighting	OBJECT-TYPE
	    SYNTAX	Weighting
	    MAX-ACCESS	read-write
	    STATUS	current
	    DESCRIPTION
		"Weighting value (0..3)"
	    REFERENCE
		"Owner Module: HO-algorithm module in L1
		 Mode-of-operation: set from manager
		 Effective-time: immediately"
	    ::= {hoAveragingLevParam 3}

	hoAveragingQualParam	OBJECT IDENTIFIER
--	    SYNTAX	SubStructure
--	    MAX-ACCESS	not-accessible
--	    DESCRIPTION
--		"The hoAveragingQualParam attribute contains averaging
--		 parameters for the signal quality measurements.
--		 -	The number of SACCH multiframes over which
--		 	results are averaged, i.e. the window size
--			(Hreqave in GSM 05.08).
--		-	The number of results sent in the 'handover
--			required' message (Hreqt in GSM 05.08).
--		-	Weighting"
--	    REFERENCE
--		"Owner Module: HO-algorithm module in L1
--		 Mode-of-operation: set from manager
--		 Effective-time: immediately"
	    ::= {handoverControlPackage 6}

	hoAveragingQualParamHreqave	OBJECT-TYPE
	    SYNTAX	AveragingNumber
	    MAX-ACCESS	read-write
	    STATUS	current
	    DESCRIPTION
		"Refer to GSM 05.08 (Hreqave)"
	    REFERENCE
		"Owner Module: HO-algorithm module in L1
		 Mode-of-operation: set from manager
		 Effective-time: immediately"
	    ::= {hoAveragingQualParam 1}

	hoAveragingQualParamHreqt	OBJECT-TYPE
	    SYNTAX	AveragingNumber
	    MAX-ACCESS	read-write
	    STATUS	current
	    DESCRIPTION
		"Refer to GSM 05.08 (Hreqt)"
	    REFERENCE
		"Owner Module: HO-algorithm module in L1
		 Mode-of-operation: set from manager
		 Effective-time: immediately"
	    ::= {hoAveragingQualParam 2}

	hoAveragingQualParamWeighting	OBJECT-TYPE
	    SYNTAX	Weighting
	    MAX-ACCESS	read-write
	    STATUS	current
	    DESCRIPTION
		"Weighting value (0..3)"
	    REFERENCE
		"Owner Module: HO-algorithm module in L1
		 Mode-of-operation: set from manager
		 Effective-time: immediately"
	    ::= {hoAveragingQualParam 3}

	hoMarginDef	OBJECT-TYPE
	    SYNTAX	HoMargin
	    MAX-ACCESS	read-write
	    STATUS	current
	    DESCRIPTION
		"The value of this attribute is used as a threshold to
		 prevent repetitive hand-over between adjacent cells,
		 in case the handover is caused by received signal level
		 or the power budget process. Refer to Annex A of
		 Specification GSM 05.08 (HO_MARGIN (n))."
	    REFERENCE
		"Owner Module: HO-algorithm module in L1
		 Mode-of-operation: set from manager
		 Effective-time: immediately"
		DEFVAL
		 {6}
	    ::= {handoverControlPackage 7}

	hoThresholdDistParam	OBJECT IDENTIFIER
--	    SYNTAX	SubStructure
--	    MAX-ACCESS	not-accessible
--	    DESCRIPTION
--		"The hoThresholdDistParam attribute contains parameters
--		 used in the handover process, in case the handover cause
--		 is distance between the Mobile Station and the BTS. See
--		 Specification GSM 05.08.
--
--		 -	The number of distance measurements that have to
--			be taken into account, when making a handover
--		 	decision, reason distance overflow (N8).
--		 -	The number of distances (out of total measurements)
--			that have to be greater than the maximum distance,
--			before making a handover decision (P8).
--		 -	The maximum timing advance (or distance) between
--			the BTS and the MS which can be expressed in units
--			of timing advance or km.
--
--		 Refer to Specification GSM 05.08 (MS_RANGE_MAX)."
--	    REFERENCE
--		"Owner Module: HO-algorithm module in L1
--		 Mode-of-operation: set from manager
--		 Effective-time: immediately"
	    ::= {handoverControlPackage 8}

	hoThresholdDistParamTimeadv	OBJECT-TYPE
	    SYNTAX	MSRangeMax
	    MAX-ACCESS	read-write
	    STATUS	current
	    DESCRIPTION
		"Timing Advance. In units of km compatible with Phase 1."
	    REFERENCE
		"Owner Module: HO-algorithm module in L1
		 Mode-of-operation: set from manager
		 Effective-time: immediately"
	    ::= {hoThresholdDistParam 1}

	hoThresholdDistParamP8	OBJECT-TYPE
	    SYNTAX	AveragingNumber
	    MAX-ACCESS	read-write
	    STATUS	current
	    DESCRIPTION
		"Refer to GSM 05.08 (P8)"
	    REFERENCE
		"Owner Module: HO-algorithm module in L1
		 Mode-of-operation: set from manager
		 Effective-time: immediately"
	    ::= {hoThresholdDistParam 2}

	hoThresholdDistParamN8	OBJECT-TYPE
	    SYNTAX	AveragingNumber
	    MAX-ACCESS	read-write
	    STATUS	current
	    DESCRIPTION
		"Refer to GSM 05.08 (N8)"
	    REFERENCE
		"Owner Module: HO-algorithm module in L1
		 Mode-of-operation: set from manager
		 Effective-time: immediately"
	    ::= {hoThresholdDistParam 3}

	hoThresholdInterfaceParam	OBJECT IDENTIFIER
--	    SYNTAX	SubStructure
--	    MAX-ACCESS	not-accessible
--	    DESCRIPTION
--		"The hoThresholdInterferenceParam attribute contains
--		 parameters for comparing the averaged uplink and downlink
--		 interference measurements. See Specification GSM 05.08.
--
--		 - 	Threshold level for handover, reason interference
--			(RXLEV_UL_IH).
--		 -	Threshold level for handover, reason interference
--			(RXLEV_DL_IH).
--		 -	The number of averages that have to be taken into
--			account, when making a handover decision (N7).
--		 -	The number of averages (out of total averages) that
--			have to be higher/lower than the threshold, before
--			making a handover decision (P7)."
--	    REFERENCE
--		"Owner Module: HO-algorithm module in L1
--		 Mode-of-operation: set from manager
--		 Effective-time: immediately"
	    ::= {handoverControlPackage 9}

	hoThresholdInterfaceParamRxLevelUL	OBJECT-TYPE
	    SYNTAX	RxLev
	    MAX-ACCESS	read-write
	    STATUS	current
	    DESCRIPTION
		"Refer to GSM 05.08 (rxLevelUL)."
	    REFERENCE
		"Owner Module: HO-algorithm module in L1
		 Mode-of-operation: set from manager
		 Effective-time: immediately"
	    ::= {hoThresholdInterfaceParam 1}

	hoThresholdInterfaceParamRxLevelDL	OBJECT-TYPE
	    SYNTAX	RxLev
	    MAX-ACCESS	read-write
	    STATUS	current
	    DESCRIPTION
		"Refer to GSM 05.08 (rxLevelDL)."
	    REFERENCE
		"Owner Module: HO-algorithm module in L1
		 Mode-of-operation: set from manager
		 Effective-time: immediately"
	    ::= {hoThresholdInterfaceParam 2}

	hoThresholdInterfaceParamPx	OBJECT-TYPE
	    SYNTAX	AveragingNumber
	    MAX-ACCESS	read-write
	    STATUS	current
	    DESCRIPTION
		"Refer to GSM 05.08 (Px)"
	    REFERENCE
		"Owner Module: HO-algorithm module in L1
		 Mode-of-operation: set from manager
		 Effective-time: immediately"
	    ::= {hoThresholdInterfaceParam 3}

	hoThresholdInterfaceParamNx	OBJECT-TYPE
	    SYNTAX	AveragingNumber
	    MAX-ACCESS	read-write
	    STATUS	current
	    DESCRIPTION
		"Refer to GSM 05.08 (Nx)"
	    REFERENCE
		"Owner Module: HO-algorithm module in L1
		 Mode-of-operation: set from manager
		 Effective-time: immediately"
	    ::= {hoThresholdInterfaceParam 4}

	hoThresholdLevParam	OBJECT IDENTIFIER
--	    SYNTAX	SubStructure
--	    MAX-ACCESS	not-accessible
--	    DESCRIPTION
--		"The hoThresholdLevParam attribute contains parameters
--		 for comparing averaged uplink and downlink signal strength
--		 measurements. See Specification GSM 05.08.
--
--		 -	Threshold level for handover, reason uplink signal
--			strength (L_RXLEV_UL_H).
--		 -	Threshold level for handover, reason downlink signal
--			strength (L_RXLEV_DL_H).
--		 -	The number of averages that have to be taken into
--			account, when making a handover decision (N5).
--		 -	The number of averages (out of total averages) that
--			have to be upper/lower than the threshold, before
--			making a handover decision (P5)."
--	    REFERENCE
--		"Owner Module: HO-algorithm module in L1
--		 Mode-of-operation: set from manager
--		 Effective-time: immediately"
	    ::= {handoverControlPackage 10}

	hoThresholdLevParamRxLevelUL	OBJECT-TYPE
	    SYNTAX	RxLev
	    MAX-ACCESS	read-write
	    STATUS	current
	    DESCRIPTION
		"Refer to GSM 05.08 (rxLevelUL)."
	    REFERENCE
		"Owner Module: HO-algorithm module in L1
		 Mode-of-operation: set from manager
		 Effective-time: immediately"
	    ::= {hoThresholdLevParam 1}

	hoThresholdLevParamRxLevelDL	OBJECT-TYPE
	    SYNTAX	RxLev
	    MAX-ACCESS	read-write
	    STATUS	current
	    DESCRIPTION
		"Refer to GSM 05.08 (rxLevelDL)."
	    REFERENCE
		"Owner Module: HO-algorithm module in L1
		 Mode-of-operation: set from manager
		 Effective-time: immediately"
	    ::= {hoThresholdLevParam 2}

	hoThresholdLevParamPx	OBJECT-TYPE
	    SYNTAX	AveragingNumber
	    MAX-ACCESS	read-write
	    STATUS	current
	    DESCRIPTION
		"Refer to GSM 05.08 (Px)"
	    REFERENCE
		"Owner Module: HO-algorithm module in L1
		 Mode-of-operation: set from manager
		 Effective-time: immediately"
		DEFVAL
		{6}
	    ::= {hoThresholdLevParam 3}

	hoThresholdLevParamNx	OBJECT-TYPE
	    SYNTAX	AveragingNumber
	    MAX-ACCESS	read-write
	    STATUS	current
	    DESCRIPTION
		"Refer to GSM 05.08 (Nx)"
	    REFERENCE
		"Owner Module: HO-algorithm module in L1
		 Mode-of-operation: set from manager
		 Effective-time: immediately"
		DEFVAL
		{8}
	    ::= {hoThresholdLevParam 4}

	hoThresholdQualParam	OBJECT IDENTIFIER
--	    SYNTAX	SubStructure
--	    MAX-ACCESS	not-accessible
--	    DESCRIPTION
--		"The hoThresholdQualParam attribute contains parameters for
--		 comparing averaged uplink and downlink signal quality
--		 measurements. See Specification GSM 05.08.
--
--		-	Threshold level for handover, reason uplink signal
--			quality (L_RXQUAL_UL_H).
--		-	Threshold level for handover, reason downlink signal
--			quality (L_RXQUAL_DL_H).
--		-	The number of averages that have to be taken into
--			account, when making a handover decision (N6).
--		-	The number of averages (out of total averages) that
--			have to be upper/lower than the threshold, before
--			making a handover decision (P6)."
	    ::= {handoverControlPackage 11}

	hoThresholdQualParamRxQualUL	OBJECT-TYPE
	    SYNTAX	RxQual
	    MAX-ACCESS	read-write
	    STATUS	current
	    DESCRIPTION
		"Refer to GSM 05.08 (rxLevelUL)."
	    REFERENCE
		"Owner Module: HO-algorithm module in L1
		 Mode-of-operation: set from manager
		 Effective-time: immediately"
	    ::= {hoThresholdQualParam 1}

	hoThresholdQualParamRxQualDL	OBJECT-TYPE
	    SYNTAX	RxQual
	    MAX-ACCESS	read-write
	    STATUS	current
	    DESCRIPTION
		"Refer to GSM 05.08 (rxLevelDL)."
	    REFERENCE
		"Owner Module: HO-algorithm module in L1
		 Mode-of-operation: set from manager
		 Effective-time: immediately"
	    ::= {hoThresholdQualParam 2}

	hoThresholdQualParamPx	OBJECT-TYPE
	    SYNTAX	AveragingNumber
	    MAX-ACCESS	read-write
	    STATUS	current
	    DESCRIPTION
		"Refer to GSM 05.08 (Px)"
	    REFERENCE
		"Owner Module: HO-algorithm module in L1
		 Mode-of-operation: set from manager
		 Effective-time: immediately"
		DEFVAL
		{3}
	    ::= {hoThresholdQualParam 3}

	hoThresholdQualParamNx	OBJECT-TYPE
	    SYNTAX	AveragingNumber
	    MAX-ACCESS	read-write
	    STATUS	current
	    DESCRIPTION
		"Refer to GSM 05.08 (Nx)"
	    REFERENCE
		"Owner Module: HO-algorithm module in L1
		 Mode-of-operation: set from manager
		 Effective-time: immediately"
		DEFVAL
		{3}
	    ::= {hoThresholdQualParam 4}

	interferenceAveragingParam	OBJECT IDENTIFIER
--	    SYNTAX	SubStructure
--	    MAX-ACCESS	not-accessible
--	    DESCRIPTION
--		"The interferenceAveragingParam attribute contains
--		 parameters used in averaging interference levels in
--		 the unallocated time slots. See Specification GSM 05.08
--		 for details.
--
--		 -	The number of SACCH multiframes over which the
--			values are averaged (INTAVE).
--		 -	Boundary limits of five interference bands for
--			the unallocated time slots. Refer to Specification
--			GSM 05.08 (O-X5). The BSS shall map the averaged
--			interference level measurements into these five
--			bands. The range of each boundary is -110...-47 dBm."
--	    REFERENCE
--		"Owner Module: HO-algorithm module in L1
--		 Mode-of-operation: set from manager
--		 Effective-time: immediately"
	    ::= {handoverControlPackage 12}

	interferenceAveragingParamAveragingPeriod	OBJECT-TYPE
	    SYNTAX	AveragingNumber
	    MAX-ACCESS	read-write
	    STATUS	current
	    DESCRIPTION
		"Refer to GSM 05.08 (INTAVE). Interference averaging period
		 in number of SACCH nultiframe (INTAVE)."
	    REFERENCE
		"Owner Module: HO-algorithm module in L1
		 Mode-of-operation: set from manager
		 Effective-time: immediately"
	    ::= {interferenceAveragingParam 1}

	interferenceAveragingParamThresholdBoundary0	OBJECT-TYPE
	    SYNTAX	RxLev
	    MAX-ACCESS	read-write
	    STATUS	current
	    DESCRIPTION
		"Interference Threshold Boundries."
	    REFERENCE
		"Owner Module: HO-algorithm module in L1
		 Mode-of-operation: set from manager
		 Effective-time: immediately"
	    ::= {interferenceAveragingParam 2}

	interferenceAveragingParamThresholdBoundary1	OBJECT-TYPE
	    SYNTAX	RxLev
	    MAX-ACCESS	read-write
	    STATUS	current
	    DESCRIPTION
		"Refer to GSM 05.08 (rxLevelDL)."
	    REFERENCE
		"Owner Module: HO-algorithm module in L1
		 Mode-of-operation: set from manager
		 Effective-time: immediately"
	    ::= {interferenceAveragingParam 3}

	interferenceAveragingParamThresholdBoundary2	OBJECT-TYPE
	    SYNTAX	RxLev
	    MAX-ACCESS	read-write
	    STATUS	current
	    DESCRIPTION
		"Interference Threshold Boundries."
	    REFERENCE
		"Owner Module: HO-algorithm module in L1
		 Mode-of-operation: set from manager
		 Effective-time: immediately"
	    ::= {interferenceAveragingParam 4}

	interferenceAveragingParamThresholdBoundary3	OBJECT-TYPE
	    SYNTAX	RxLev
	    MAX-ACCESS	read-write
	    STATUS	current
	    DESCRIPTION
		"Interference Threshold Boundries."
	    REFERENCE
		"Owner Module: HO-algorithm module in L1
		 Mode-of-operation: set from manager
		 Effective-time: immediately"
	    ::= {interferenceAveragingParam 5}

	interferenceAveragingParamThresholdBoundary4	OBJECT-TYPE
	    SYNTAX	RxLev
	    MAX-ACCESS	read-write
	    STATUS	current
	    DESCRIPTION
		"Interference Threshold Boundries."
	    REFERENCE
		"Owner Module: HO-algorithm module in L1
		 Mode-of-operation: set from manager
		 Effective-time: immediately"
	    ::= {interferenceAveragingParam 6}

	interferenceAveragingParamThresholdBoundary5	OBJECT-TYPE
	    SYNTAX	RxLev
	    MAX-ACCESS	read-write
	    STATUS	current
	    DESCRIPTION
		"Interference Threshold Boundries."
	    REFERENCE
		"Owner Module: HO-algorithm module in L1
		 Mode-of-operation: set from manager
		 Effective-time: immediately"
	    ::= {interferenceAveragingParam 7}

	msTxPwrMaxCellDef	OBJECT-TYPE
	    SYNTAX	TxPower
	    MAX-ACCESS	read-write
	    STATUS	current
	    DESCRIPTION
		"The msTxPwrMaxCell attribute is used to indicate the
		 maximum power level a MS may use in an adjacent cell.
		 The msTxPwrMaxCellDef attribute is used to evaluate
		 handover to undefined adjacent cells. See Table 1 of
		 Annex  A of Specification GSM 05.08 (MS_TXPWR_MAX (n))."
	    REFERENCE
		"Owner Module: HO-algorithm module in L1
		 Mode-of-operation: set from manager
		 Effective-time: immediately"
	    ::= {handoverControlPackage 13}

	rxLevMinCellDef	OBJECT-TYPE
	    SYNTAX	RxLev
	    MAX-ACCESS	read-write
	    STATUS	current
	    DESCRIPTION
		"The rxLevMinCellDef attribute holds the default value of
		 rxLevMinCell. It is used to evaluate handover to undefined
		 cells. See Annex A of Specification GSM 05.08 (RXLEV_MIN_DEF)"
	    REFERENCE
		"Owner Module: HO-algorithm module in L1
		 Mode-of-operation: set from manager
		 Effective-time: immediately"
	    ::= {handoverControlPackage 14}

powerControlPackage OBJECT IDENTIFIER
-- 	DESCRIPTION
-- 		"Manufacturers shall use the class powerControl as a
-- 		 base class for specifying actual object classes for
-- 		 management of parameters specific to their power
-- 		 control algorithm. The class powerControl cannot be
-- 		 instantiated. There are, at most, two instances of
-- 		 these actual instantiated subclasses per BTS, one to
-- 		 manage parameters used by the BSC and one to manage
-- 		 parameters used by the BTS. This package provides
-- 		 the attributes common to all subclasses. If BS power
-- 		 control is supported, it is assumed that the processing
-- 		 for MS and BS power control measurements are performed
-- 		 in the same place (BSC or BTS) and that the same set
-- 		 of parameters are used for both MS and BS power control
-- 		 algorithms."
	::= {gp10GsmMib 11}

	pcAveragingLev	OBJECT IDENTIFIER
--	    SYNTAX	SubStructure
--	    MAX-ACCESS	not-accessible
--	    DESCRIPTION
--		"The pcAveragingLev attribute contains averaging parameters
--		 for the signal strength measurements. The values are used
--		 in the power control process.
--
--		 -	The number of SACCH multiframes over which results are
--			averaged, i.e. the window size (Hreqave in GSM 05.08).
--		 -	The number of results sent in the 'handover required'
--			message (Hreqt in GSM 05.08).
--		 -	Weighting"
--	    REFERENCE
--		"Owner Module: L1 Power Control module
--		 Mode-of-operation: set from manager
--		 Effective-time: immediately"
	    ::= {powerControlPackage 1}

	pcAveragingLevHreqave	OBJECT-TYPE
	    SYNTAX	AveragingNumber
	    MAX-ACCESS	read-write
	    STATUS	current
	    DESCRIPTION
		"The number of SACCH multiframes over which results are
		 averaged, i.e. the window size (Hreqave in GSM 05.08)."
	    REFERENCE
		"Owner Module: L1 Power Control module
		 Mode-of-operation: set from manager
		 Effective-time: immediately"
		DEFVAL
		{2}
	    ::= {pcAveragingLev 1}

	pcAveragingLevHreqt	OBJECT-TYPE
	    SYNTAX	AveragingNumber
	    MAX-ACCESS	read-write
	    STATUS	current
	    DESCRIPTION
		"The number of results sent in the 'handover required'
		message (Hreqt in GSM 05.08)."
	    REFERENCE
		"Owner Module: L1 Power Control module
		 Mode-of-operation: set from manager
		 Effective-time: immediately"
	    ::= {pcAveragingLev 2}

	pcAveragingLevWeighting	OBJECT-TYPE
	    SYNTAX	Weighting
	    MAX-ACCESS	read-write
	    STATUS	current
	    DESCRIPTION
		"Weighting value (0..3)"
	    REFERENCE
		"Owner Module: L1 Power Control module
		 Mode-of-operation: set from manager
		 Effective-time: immediately"
	    ::= {pcAveragingLev 3}

	pcAveragingQual	OBJECT IDENTIFIER
--	    SYNTAX	SubStructure
--	    MAX-ACCESS	not-accessible
--	    DESCRIPTION
--		"The pcAveragingQual attribute contains averaging parameters
--		 for the signal quality measurements. The values are used in
--		 the power control process.
--
--		 -	The number of SACCH multiframes over which results are
--			averaged, i.e. the window size (Hreqave in GSM 05.08).
--		 -	The number of results sent in the 'handover required'
--			message (Hreqt in GSM 05.08).
--		 -	Weighting"
--	    REFERENCE
--		"Owner Module: L1 Power Control module
--		 Mode-of-operation: set from manager
--		 Effective-time: immediately"
	    ::= {powerControlPackage 2}

	pcAveragingQualHreqave	OBJECT-TYPE
	    SYNTAX	AveragingNumber
	    MAX-ACCESS	read-write
	    STATUS	current
	    DESCRIPTION
		"The number of SACCH multiframes over which results are
		 averaged, i.e. the window size (Hreqave in GSM 05.08)."
	    REFERENCE
		"Owner Module: L1 Power Control module
		 Mode-of-operation: set from manager
		 Effective-time: immediately"
		DEFVAL
		{2}
	    ::= {pcAveragingQual 1}

	pcAveragingQualHreqt	OBJECT-TYPE
	    SYNTAX	AveragingNumber
	    MAX-ACCESS	read-write
	    STATUS	current
	    DESCRIPTION
		"The number of results sent in the 'handover required'
		message (Hreqt in GSM 05.08)."
	    REFERENCE
		"Owner Module: L1 Power Control module
		 Mode-of-operation: set from manager
		 Effective-time: immediately"
	    ::= {pcAveragingQual 2}

	pcAveragingQualWeighting	OBJECT-TYPE
	    SYNTAX	Weighting
	    MAX-ACCESS	read-write
	    STATUS	current
	    DESCRIPTION
		"Weighting value (0..3)"
	    REFERENCE
		"Owner Module: L1 Power Control module
		 Mode-of-operation: set from manager
		 Effective-time: immediately"
	    ::= {pcAveragingQual 3}

	pcLowerThresholdLevParam	OBJECT IDENTIFIER
--	    SYNTAX	SubStructure
--	    MAX-ACCESS	not-accessible
--	    DESCRIPTION
--		"The pcLowerThresholdLevParam attribute contains the lower
--		 thresholds for the uplink and downlink signal strength.
--		 The values are used in the power control process. See
--		 Specification GSM 05.08.
--
--		 -	Threshold level for uplink power increase
--			(L_RXLEV_UL_P).
--		 -	Threshold level for downlink power increase
--			(L_RXLEV_DL_P).
--		 -	The total number of averages that  have to be taken
--			into account before power increase decision (N1).
--		 -	The number of averages (out of total averages) that 
--			have to be lower than the threshold, before making a
--			power increase decision (P1)."
--	    REFERENCE
--		"Owner Module: L1 Power Control module
--		 Mode-of-operation: set from manager
--		 Effective-time: immediately"
	    ::= {powerControlPackage 3}

	pcLowerThresholdLevParamRxLevelUL	OBJECT-TYPE
	    SYNTAX	RxLev
	    MAX-ACCESS	read-write
	    STATUS	current
	    DESCRIPTION
		"Threshold level for uplink power increase (L_RXLEV_UL_P)."
	    REFERENCE
		"Owner Module: L1 Power Control module
		 Mode-of-operation: set from manager
		 Effective-time: immediately"
	    ::= {pcLowerThresholdLevParam 1}

	pcLowerThresholdLevParamRxLevelDL	OBJECT-TYPE
	    SYNTAX	RxLev
	    MAX-ACCESS	read-write
	    STATUS	current
	    DESCRIPTION
		"Threshold level for downlink power increase (L_RXLEV_DL_P)."
	    REFERENCE
		"Owner Module: L1 Power Control module
		 Mode-of-operation: set from manager
		 Effective-time: immediately"
	    ::= {pcLowerThresholdLevParam 2}

	pcLowerThresholdLevParamPx	OBJECT-TYPE
	    SYNTAX	AveragingNumber
	    MAX-ACCESS	read-write
	    STATUS	current
	    DESCRIPTION
		"The number of averages (out of total averages) that 
		 have to be lower than the threshold, before making a
		 power increase decision (P1)."
	    REFERENCE
		"Owner Module: L1 Power Control module
		 Mode-of-operation: set from manager
		 Effective-time: immediately"
	    ::= {pcLowerThresholdLevParam 3}

	pcLowerThresholdLevParamNx	OBJECT-TYPE
	    SYNTAX	AveragingNumber
	    MAX-ACCESS	read-write
	    STATUS	current
	    DESCRIPTION
		"The total number of averages that have to be taken
		 into account before power increase decision (N1)."
	    REFERENCE
		"Owner Module: L1 Power Control module
		 Mode-of-operation: set from manager
		 Effective-time: immediately"
	    ::= {pcLowerThresholdLevParam 4}

	pcLowerThresholdQualParam	OBJECT IDENTIFIER
--	    SYNTAX	SubStructure
--	    MAX-ACCESS	not-accessible
--	    DESCRIPTION
--		"The pcLowerThresholdQualParam attribute contains the
--		 lower thresholds for the uplink and downlink signal
--		 quality. The values are used in the power control
--		 process. See Specification GSM 05.08.
--
--		 -	Threshold level for uplink power increase
--			(L_RXQUAL_UL_P).
--		 -	Threshold level for downlink power increase
--			(L_RXQUAL_DL_P).
--		 -	The total number of averages that  have to be taken
--			into account before power increase decision (N3).
--		 -	The number of averages (out of total averages) that
--			have to be lower than the threshold, before making a
--			power increase decision (P3)."
--	    REFERENCE
--		"Owner Module: L1 Power Control module
--		 Mode-of-operation: set from manager
--		 Effective-time: immediately"
	    ::= {powerControlPackage 4}

	pcLowerThresholdQualParamRxQualUL	OBJECT-TYPE
	    SYNTAX	RxQual
	    MAX-ACCESS	read-write
	    STATUS	current
	    DESCRIPTION
		"Threshold level for uplink power increase (L_RXQUAL_UL_P)."
	    REFERENCE
		"Owner Module: L1 Power Control module
		 Mode-of-operation: set from manager
		 Effective-time: immediately"
	    ::= {pcLowerThresholdQualParam 1}

	pcLowerThresholdQualParamRxQualDL	OBJECT-TYPE
	    SYNTAX	RxQual
	    MAX-ACCESS	read-write
	    STATUS	current
	    DESCRIPTION
		"Threshold level for downlink power increase (L_RXQUAL_DL_P)."
	    REFERENCE
		"Owner Module: L1 Power Control module
		 Mode-of-operation: set from manager
		 Effective-time: immediately"
	    ::= {pcLowerThresholdQualParam 2}

	pcLowerThresholdQualParamPx	OBJECT-TYPE
	    SYNTAX	AveragingNumber
	    MAX-ACCESS	read-write
	    STATUS	current
	    DESCRIPTION
		"The number of averages (out of total averages) that 
		 have to be lower than the threshold, before making a
		 power increase decision (P3)."
	    REFERENCE
		"Owner Module: L1 Power Control module
		 Mode-of-operation: set from manager
		 Effective-time: immediately"
	    ::= {pcLowerThresholdQualParam 3}

	pcLowerThresholdQualParamNx	OBJECT-TYPE
	    SYNTAX	AveragingNumber
	    MAX-ACCESS	read-write
	    STATUS	current
	    DESCRIPTION
		"The total number of averages that have to be taken
		 into account before power increase decision (N3)."
	    REFERENCE
		"Owner Module: L1 Power Control module
		 Mode-of-operation: set from manager
		 Effective-time: immediately"
	    ::= {pcLowerThresholdQualParam 4}

	pcUpperThresholdLevParam	OBJECT IDENTIFIER
--	    SYNTAX	SubStructure
--	    MAX-ACCESS	not-accessible
--	    DESCRIPTION
--		"The pcUpperThresholdLevParam attribute contains the upper
--		 thresholds for the uplink and downlink signal strength.
--		 The values are used in the power control process. See
--		 Specification GSM 05.08.
--
--		 -	Threshold level for uplink power reduction
--			(U_RXLEV_UL_P).
--		 -	Threshold level for downlink power reduction
--			(U_RXLEV_DL_P).
--		 -	The total number of averages that  have to be taken
--			into account before power reduction decision (N2).
--		 -	The number of averages (out of total averages) that
--			have to be lower than the threshold, before making
--			a power reduction decision (P2)."
--	    REFERENCE
--		"Owner Module: L1 Power Control module
--		 Mode-of-operation: set from manager
--		 Effective-time: immediately"
	    ::= {powerControlPackage 5}

	pcUpperThresholdLevParamRxLevelUL	OBJECT-TYPE
	    SYNTAX	RxLev
	    MAX-ACCESS	read-write
	    STATUS	current
	    DESCRIPTION
		"Threshold level for uplink power reduction (U_RXLEV_UL_P)."
	    REFERENCE
		"Owner Module: L1 Power Control module
		 Mode-of-operation: set from manager
		 Effective-time: immediately"
	    ::= {pcUpperThresholdLevParam 1}

	pcUpperThresholdLevParamRxLevelDL	OBJECT-TYPE
	    SYNTAX	RxLev
	    MAX-ACCESS	read-write
	    STATUS	current
	    DESCRIPTION
		"Threshold level for downlink power reduction (U_RXLEV_DL_P)."
	    REFERENCE
		"Owner Module: L1 Power Control module
		 Mode-of-operation: set from manager
		 Effective-time: immediately"
	    ::= {pcUpperThresholdLevParam 2}

	pcUpperThresholdLevParamPx	OBJECT-TYPE
	    SYNTAX	AveragingNumber
	    MAX-ACCESS	read-write
	    STATUS	current
	    DESCRIPTION
		"The number of averages (out of total averages) that 
		 have to be lower than the threshold, before making a
		 power reduction decision (P2)."
	    REFERENCE
		"Owner Module: L1 Power Control module
		 Mode-of-operation: set from manager
		 Effective-time: immediately"
	    ::= {pcUpperThresholdLevParam 3}

	pcUpperThresholdLevParamNx	OBJECT-TYPE
	    SYNTAX	AveragingNumber
	    MAX-ACCESS	read-write
	    STATUS	current
	    DESCRIPTION
		"The total number of averages that have to be taken
		 into account before power reduction decision (N2)."
	    REFERENCE
		"Owner Module: L1 Power Control module
		 Mode-of-operation: set from manager
		 Effective-time: immediately"
	    ::= {pcUpperThresholdLevParam 4}


	pcUpperThresholdQualParam	OBJECT IDENTIFIER
--	    SYNTAX	SubStructure
--	    MAX-ACCESS	not-accessible
--	    DESCRIPTION
--		"The pcUpperThresholdQualParam attribute contains the
--		 upper thresholds for the uplink and downlink signal
--		 quality. The values are used in the power control
--		 process. See Specification GSM 05.08.
--
--		 -	Threshold level for uplink power reduction
--			(U_RXQUAL_UL_P).
--		 -	Threshold level for downlink power reduction
--			(U_RXQUAL_DL_P).
--		 -	The total number of averages that  have to be taken
--			into account before power reduction decision (N4).
--		 -	The number of averages (out of total averages) that
--			have to be lower than the threshold, before making
--			a power reduction decision (P4)."
--	    REFERENCE
--		"Owner Module: L1 Power Control module
--		 Mode-of-operation: set from manager
--		 Effective-time: immediately"
	    ::= {powerControlPackage 6}

	pcUpperThresholdQualParamRxQualUL	OBJECT-TYPE
	    SYNTAX	RxQual
	    MAX-ACCESS	read-write
	    STATUS	current
	    DESCRIPTION
		"Threshold level for uplink power reduction (U_RXQUAL_UL_P)."
	    REFERENCE
		"Owner Module: L1 Power Control module
		 Mode-of-operation: set from manager
		 Effective-time: immediately"
	    ::= {pcUpperThresholdQualParam 1}

	pcUpperThresholdQualParamRxQualDL	OBJECT-TYPE
	    SYNTAX	RxQual
	    MAX-ACCESS	read-write
	    STATUS	current
	    DESCRIPTION
		"Threshold level for downlink power reduction (U_RXQUAL_DL_P)."
	    REFERENCE
		"Owner Module: L1 Power Control module
		 Mode-of-operation: set from manager
		 Effective-time: immediately"
	    ::= {pcUpperThresholdQualParam 2}

	pcUpperThresholdQualParamPx	OBJECT-TYPE
	    SYNTAX	AveragingNumber
	    MAX-ACCESS	read-write
	    STATUS	current
	    DESCRIPTION
		"The number of averages (out of total averages) that 
		 have to be lower than the threshold, before making a
		 power reduction decision (P4)."
	    REFERENCE
		"Owner Module: L1 Power Control module
		 Mode-of-operation: set from manager
		 Effective-time: immediately"
	    ::= {pcUpperThresholdQualParam 3}

	pcUpperThresholdQualParamNx	OBJECT-TYPE
	    SYNTAX	AveragingNumber
	    MAX-ACCESS	read-write
	    STATUS	current
	    DESCRIPTION
		"The total number of averages that have to be taken
		 into account before power reduction decision (N4)."
	    REFERENCE
		"Owner Module: L1 Power Control module
		 Mode-of-operation: set from manager
		 Effective-time: immediately"
	    ::= {pcUpperThresholdQualParam 4}

	powerControlInterval	OBJECT-TYPE
	    SYNTAX	PowerControlInterval
	    MAX-ACCESS	read-write
	    STATUS	current
	    DESCRIPTION
		"The powerControlInterval attribute contains the minimum
		 interval between successive modifications of the RF power
		 level. Refer to the Specification GSM 05.08 (P_Con_INTERVAL).
		 The range is 0...30 seconds and the step size 0.96 seconds."
	    REFERENCE
		"Owner Module: L1 Power Control module
		 Mode-of-operation: set from manager
		 Effective-time: immediately"
	    ::= {powerControlPackage 7}

	powerIncrStepSize	OBJECT-TYPE
	    SYNTAX	PowerIncrStepSize
	    MAX-ACCESS	read-write
	    STATUS	current
	    DESCRIPTION
		"The powerIncrStepSize attribute defines the step size
		 used when increasing the MS transmit power. The step
		 size is 2, 4 or 6 dB. Refer to Specification GSM 05.08
		 (Pow_Incr_Step_Size)."
	    REFERENCE
		"Owner Module: L1 Power Control module
		 Mode-of-operation: set from manager
		 Effective-time: immediately"
	    ::= {powerControlPackage 8}

	powerRedStepSize	OBJECT-TYPE
	    SYNTAX	PowerRedStepSize
	    MAX-ACCESS	read-write
	    STATUS	current
	    DESCRIPTION
		"The powerRedStepSize attribute defines the step size
		 used when reducing the MS transmit power. The step
		 size is 2 or 4 dB. Refer to Specification GSM 05.08
		 (Pow_Red_Step_Size)."
	    REFERENCE
		"Owner Module: L1 Power Control module
		 Mode-of-operation: set from manager
		 Effective-time: immediately"
	    ::= {powerControlPackage 9}

cellMeasurmentPackage OBJECT IDENTIFIER
-- 	DESCRIPTION
-- 		"Measurements related to the BTS.
-- 		 CELL Measurement Function."
	::= {gp10GsmMib 12}

	meanPCHAGCHQueueLength	OBJECT-TYPE
	    SYNTAX	INTEGER
	    MAX-ACCESS	read-write
	    STATUS	current
	    DESCRIPTION
		"Mean PCH-AGCH queue length:

		 This measurement provides the arithmetic mean of the number
		 of all messages waiting for transmission on the PCH-AGCH.

		 This measurement is obtained by sampling at a pre-defined
		 interval (System designed), the PCH-AGCH queue length and
		 then taking the arithmetic mean (GSM 04.08 [2])."
	    REFERENCE
		"Owner Module: RRM module
		 Mode-of-operation: set from RRM
		 Effective-time: immediately according current measurement interval"
	    ::= {cellMeasurmentPackage 1}

	attTransOfPagingMessagesThePCH	OBJECT-TYPE
	    SYNTAX	INTEGER
	    MAX-ACCESS	read-write
	    STATUS	current
	    DESCRIPTION
		"Attempted Transmission of Paging Messages (the PCH):

		 This measurement provides the number of Paging messages
		 transmitted (these are counted as attempts).

		 This is value is updated upon transmission of 'PAGING
		 REQUEST' (GSM 04.08 [2])."
	    REFERENCE
		"Owner Module: RRM module
		 Mode-of-operation: set from RRM
		 Effective-time: immediately according current measurement interval"
	    ::= {cellMeasurmentPackage 2}


	unsuccTransOfPagingMessagesThePCH	OBJECT-TYPE
	    SYNTAX	INTEGER
	    MAX-ACCESS	read-write
	    STATUS	current
	    DESCRIPTION
		"Unsuccessful Transmission of Paging Messages (the PCH)

		 This measurement provides the number of unsuccessful
		 Paging requests.

		 This value is updated when a no 'PAGING RESPONSE' received for
		 the 'PAGING REQUEST', expiry of timer T3113 (GSM 04.08 [2])."
	    REFERENCE
		"Owner Module: RRM module
		 Mode-of-operation: set from RRM
		 Effective-time: immediately according current measurement interval"
	    ::= {cellMeasurmentPackage 3}

	attImmediateAssingProcs	OBJECT-TYPE
	    SYNTAX	INTEGER
	    MAX-ACCESS	read-write
	    STATUS	current
	    DESCRIPTION
		"Attempted IMMEDIATE ASSIGNMENT Procedures:

		 This measurement provides the number of attempted immediate
		 assignment procedures.

		 This value is updated upon receipt of 'CHANNEL REQUIRED'
		 Message. Note, the establishment causes are: 'EMERGENCY
		 CALL', 'CALL RE-ESTABLISHMENT', 'ANSWER TO PAGING',
		 'ORIGINATING CALL' , 'LOCATION UPDATING' and 'OTHER
		 PROCEDURES' as defined in (GSM 04.08 [2])."
	    REFERENCE
		"Owner Module: RRM module
		 Mode-of-operation: set from RRM
		 Effective-time: immediately according current measurement interval"
	    ::= {cellMeasurmentPackage 4}

	succImmediateAssingProcs	OBJECT-TYPE
	    SYNTAX	INTEGER
	    MAX-ACCESS	read-write
	    STATUS	current
	    DESCRIPTION
		"Successful IMMEDIATE ASSIGNMENT Procedures:

		 This measurement provides the number of successful immediate
		 assignment procedures.

		 Transmission of 'IMMEDIATE ASSIGN COMMAND' Message. This
		 message contains either an 'IMMEDIATE ASSIGNMENT' Message
		 or an 'IMMEDIATE ASSIGNMENT EXTENDED' Message. If an
		 'IMMEDIATE ASSIGNMENT EXTENDED' Message is transmitted,
		 the counter shall be incremented by two, because that
		 Message contains assignment information for two mobiles
		 (GSM 04.08 [2])."
	    REFERENCE
		"Owner Module: RRM module
		 Mode-of-operation: set from RRM
		 Effective-time: immediately according current measurement interval"
	    ::= {cellMeasurmentPackage 5}

	attImmediateAssingProcsPerCauseTable	OBJECT-TYPE
	    SYNTAX	SEQUENCE OF AttImmediateAssingProcsPerCauseEntry
	    MAX-ACCESS	not-accessible
	    STATUS	current
	    DESCRIPTION
		"This entry is required to define a table of values."
	    REFERENCE
		"Owner Module: RRM module
		 Mode-of-operation: set from RRM
		 Effective-time: immediately according current measurement interval"
	    ::= {cellMeasurmentPackage 6}

	attImmediateAssingProcsPerCauseEntry	OBJECT-TYPE
	    SYNTAX	AttImmediateAssingProcsPerCauseEntry
	    MAX-ACCESS	not-accessible
	    STATUS	current
	    DESCRIPTION
		"Attempted IMMEDIATE ASSIGNMENT Procedures, per cause:

		 This measurement provides the number of attempted immediate
		 assignment procedures, per cause.

		 Receipt of 'CHANNEL REQUIRED' Message. Note, the establishment
		 causes are: 'EMERGENCY CALL', 'CALL RE-ESTABLISHMENT',
		 'ANSWER TO PAGING', 'ORIGINATING CALL' , 'LOCATION UPDATING'
		 and 'OTHER PROCEDURES' as defined in (GSM 04.08 [2])."
	    REFERENCE
		"Owner Module: RRM module
		 Mode-of-operation: set from RRM
		 Effective-time: immediately according current measurement interval"
	    INDEX	{attImmediateAssingProcsCause}
	    --DEFAULT cookie MIBT_%n
	    ::= {attImmediateAssingProcsPerCauseTable 1}

	AttImmediateAssingProcsPerCauseEntry	::= SEQUENCE {
	    attImmediateAssingProcsCause		CauseCode,
	    attImmediateAssingProcsValue		INTEGER
	}

	attImmediateAssingProcsCause	OBJECT-TYPE
	    SYNTAX	CauseCode
	    MAX-ACCESS	read-only
	    STATUS	current
	    DESCRIPTION
		"Cause of the service rejection."
	    REFERENCE
		"Owner Module: RRM module
		 Mode-of-operation: set from RRM
		 Effective-time: immediately according current measurement interval"
	    ::= {attImmediateAssingProcsPerCauseEntry 1}

	attImmediateAssingProcsValue	OBJECT-TYPE
	    SYNTAX	INTEGER
	    MAX-ACCESS	read-write
	    STATUS	current
	    DESCRIPTION
		"Counter of the number of rejections for the service."
	    REFERENCE
		"Owner Module: RRM module
		 Mode-of-operation: set from RRM
		 Effective-time: immediately according current measurement interval"
	    ::= {attImmediateAssingProcsPerCauseEntry 2}

	succImmediateAssingProcsPerCauseTable	OBJECT-TYPE
	    SYNTAX	SEQUENCE OF SuccImmediateAssingProcsPerCauseEntry
	    MAX-ACCESS	not-accessible
	    STATUS	current
	    DESCRIPTION
		"This entry is required to define a table of values."
	    REFERENCE
		"Owner Module: RRM module
		 Mode-of-operation: set from RRM
		 Effective-time: immediately according current measurement interval"
	    ::= {cellMeasurmentPackage 7}

	succImmediateAssingProcsPerCauseEntry	OBJECT-TYPE
	    SYNTAX	SuccImmediateAssingProcsPerCauseEntry
	    MAX-ACCESS	not-accessible
	    STATUS	current
	    DESCRIPTION
		"Successful IMMEDIATE ASSIGNMENT Procedures, per cause:

		 This measurement provides the number of successful immediate
		 assignment procedures, per cause.

		 This value is updated upon transmission of 'IMMEDIATE ASSIGN
		 COMMAND' Message. This Message contains either an 'IMMEDIATE
		 ASSIGNMENT' Message or an 'IMMEDIATE ASSIGNMENT EXTENDED'
		 Message, per cause. Note, the establishment causes are:
		 'EMERGENCY CALL', 'CALL RE-ESTABLISHMENT', 'ANSWER TO PAGING',
		 'ORIGINATING CALL' , 'LOCATION UPDATING' and 'OTHER
		 PROCEDURES'. The 'IMMEDIATE ASSIGNMENT EXTENDED' Message
		 contains assignment information for two mobiles (GSM04.08[2]).
		 If the establishment cause is identical for the the two mobile
		 stations, the counter shall be incremented by two. Otherwise
		 the affected counters shall be incremented by one."
	    REFERENCE
		"Owner Module: RRM module
		 Mode-of-operation: set from RRM
		 Effective-time: immediately according current measurement interval"
	    INDEX	{succImmediateAssingProcsCause}
	    --DEFAULT cookie MIBT_%n
	    ::= {succImmediateAssingProcsPerCauseTable 1}

	SuccImmediateAssingProcsPerCauseEntry	::= SEQUENCE {
	    succImmediateAssingProcsCause		CauseCode,
	    succImmediateAssingProcsValue		INTEGER
	}

	succImmediateAssingProcsCause	OBJECT-TYPE
	    SYNTAX	CauseCode
	    MAX-ACCESS	read-only
	    STATUS	current
	    DESCRIPTION
		"Cause of the service rejection."
	    REFERENCE
		"Owner Module: RRM module
		 Mode-of-operation: set from RRM
		 Effective-time: immediately according current measurement interval"
	    ::= {succImmediateAssingProcsPerCauseEntry 1}

	succImmediateAssingProcsValue	OBJECT-TYPE
	    SYNTAX	INTEGER
	    MAX-ACCESS	read-write
	    STATUS	current
	    DESCRIPTION
		"Counter of the number of rejections for the service."
	    REFERENCE
		"Owner Module: RRM module
		 Mode-of-operation: set from RRM
		 Effective-time: immediately according current measurement interval"
	    ::= {succImmediateAssingProcsPerCauseEntry 2}

	nbrOfPagesDiscardedFromPCHQueue	OBJECT-TYPE
	    SYNTAX	INTEGER
	    MAX-ACCESS	read-write
	    STATUS	current
	    DESCRIPTION
		"Number of Pages Discarded from the PCH Queue:

		 This measurement provides the number of Paging messages
		 which are discarded from the PCH queue before they could
		 be transmitted.

		 Pages can be discarded from the queues (assuming queuing
		 is in operation) for a number of reasons, including queue
		 overflow, priority insertion in the queue causing an overflow
		 and in-queue timer expiry (GSM 04.08 [2])."
	    REFERENCE
		"Owner Module: RRM module
		 Mode-of-operation: set from RRM
		 Effective-time: immediately according current measurement interval"
	    ::= {cellMeasurmentPackage 8}


	meanDurationOfSuccPagingProcs	OBJECT-TYPE
	    SYNTAX	INTEGER
	    MAX-ACCESS	read-write
	    STATUS	current
	    DESCRIPTION
		"Mean duration of a successful Paging Procedure:

		 This measurement provides the arithmetic mean duration of a
		 successful Paging procedure, i.e. from transmission of the
		 page request towards the BSCs and receipt of a positive
		 response.

		 An accumulation is performed for the time taken by each
		 Paging procedure during the granularity period and an
		 arithmetic mean is taken from the observed values. The
		 measured time will be between Transmission of a 'PAGING
		 REQUEST' service request to Receipt of 'PAGING RESPONSE'
		 service confirmation (GSM 04.08 [2])."
	    REFERENCE
		"Owner Module: RRM module
		 Mode-of-operation: set from RRM
		 Effective-time: immediately according current measurement interval"
	    ::= {cellMeasurmentPackage 9}

	nbrOfAvailableTCHs	OBJECT-TYPE
	    SYNTAX	INTEGER
	    MAX-ACCESS	read-write
	    STATUS	current
	    DESCRIPTION
		"Number of Available TCHs:

		 This measurement provides the number of TCHs which are
		 available for use (including those which are actually in use).

		 The guage will be incremented when the TCH becomes available
		 and decremented when it becomes unavailable. The TCH is
		 available when its administrative state is 'unlocked' or
		 'shuttingdown' and the operational state is 'enabled', and
		 is unavailable when its administrative state changes to
		 'locked' or operational state changes to 'disabled'. The
		 gauge value equals the number of TCHs with an administrative
		 state of 'unlocked' or 'shuttingdown' and an operational
		 state of 'enabled', (GSM 04.08 [2])."
	    REFERENCE
		"Owner Module: RRM module
		 Mode-of-operation: set from RRM
		 Effective-time: immediately according current measurement interval"
	    ::= {cellMeasurmentPackage 10}

	meanNbrOfBusyTCHs	OBJECT-TYPE
	    SYNTAX	INTEGER
	    MAX-ACCESS	read-write
	    STATUS	current
	    DESCRIPTION
		"Mean number of busy TCHs:

		 This measurement provides the arithmetic mean of the number
		 of TCHs which are simultaneously in use.

		 This measurement is obtained by sampling at a pre-defined
		 interval (System designed), the number of TCHs which are
		 carrying traffic and then taking the arithmetic mean
		 (GSM 04.08 [2])."
	    REFERENCE
		"Owner Module: RRM module
		 Mode-of-operation: set from RRM
		 Effective-time: immediately according current measurement interval"
	    ::= {cellMeasurmentPackage 11}

	maxNbrOfBusyTCHs	OBJECT-TYPE
	    SYNTAX	INTEGER
	    MAX-ACCESS	read-write
	    STATUS	current
	    DESCRIPTION
		"Maximum number of busy TCHs:

		 This measurement provides the highest recorded value for the
		 number of TCHs simultaneously in use.

		 This measurement is obtained by sampling at a pre-defined
		 interval (System designed), the number of TCHs which are
		 'busy', and then taking the maximum of all such values at
		 the end of the granularity period. TCH is busy between an
		 'ASSIGNMENT COMPLETE' Message and the complementary 'RELEASE'
		 Message, (GSM 04.08 [2])."
	    REFERENCE
		"Owner Module: RRM module
		 Mode-of-operation: set from RRM
		 Effective-time: immediately according current measurement interval"
	    ::= {cellMeasurmentPackage 12}

	meanNbrOfIdleTCHsPerInterferenceBand	OBJECT-TYPE
	    SYNTAX	INTEGER
	    MAX-ACCESS	read-write
	    STATUS	current
	    DESCRIPTION
		"Mean number of idle TCHs per interference band:

		 This measurement provides the arithmetic mean of the number
		 of idle TCHs per interference band. The TCH is said to be
		 idle if it can be allocated for a request. Idle TCHs are
		 allocated in five classes (GSM 05.01) depending on the
		 measured interference level.

		 This measurement is obtained by sampling at a pre-defined
		 interval (System designed), the number of idle TCHs per
		 interference band and then taking the arithmetic mean
		 (GSM 04.08 [2])."
	    REFERENCE
		"Owner Module: RRM module
		 Mode-of-operation: set from RRM
		 Effective-time: immediately according current measurement interval"
	    ::= {cellMeasurmentPackage 13}

	attTCHSeizures	OBJECT-TYPE
	    SYNTAX	INTEGER
	    MAX-ACCESS	read-write
	    STATUS	current
	    DESCRIPTION
		"Attempted TCH seizures:

		 This measurement provides the number of attempted TCH seizures

		 This value is updated upon transmission of 'ASSIGNMENT
		 COMMAND' Message to the MS, (GSM 04.08 [2])."
	    REFERENCE
		"Owner Module: RRM module
		 Mode-of-operation: set from RRM
		 Effective-time: immediately according current measurement interval"
	    ::= {cellMeasurmentPackage 14}

	succTCHSeizures	OBJECT-TYPE
	    SYNTAX	INTEGER
	    MAX-ACCESS	read-write
	    STATUS	current
	    DESCRIPTION
		"Successful TCH seizures:

		 This measurement provides the number of successful TCH
		 seizures.

		 This value is updated upon receipt of 'ASSIGNMENT COMPLETE'
		 Message from the MS, (GSM 04.08 [2])."
	    REFERENCE
		"Owner Module: RRM module
		 Mode-of-operation: set from RRM
		 Effective-time: immediately according current measurement interval"
	    ::= {cellMeasurmentPackage 15}

	attTCHSeizuresMeetingTCHBlockedState	OBJECT-TYPE
	    SYNTAX	INTEGER
	    MAX-ACCESS	read-write
	    STATUS	current
	    DESCRIPTION
		"Attempted TCH Seizures meeting an TCH blocked state:

		 This measurement provides the number of attempted TCH
		 seizures meeting all busy TCH state.

		 This value is updated upon receipt of 'SETUP' Message from
		 the MS meeting all TCH busy state (GSM 04.08 [2])."
	    REFERENCE
		"Owner Module: RRM module
		 Mode-of-operation: set from RRM
		 Effective-time: immediately according current measurement interval"
	    ::= {cellMeasurmentPackage 16}

	allAvailableTCHAllocatedTime	OBJECT-TYPE
	    SYNTAX	INTEGER
	    MAX-ACCESS	read-write
	    STATUS	current
	    DESCRIPTION
		"All Available TCH Allocated Time:

		 This measurement provides the accumulated time during the
		 granularity period when all available TCHs were in use or
		 otherwise unavailable to be allocated.

		 Each time segment represents the elapsed time from the last
		 available TCH being allocated to the next occurrence of a
		 release of a TCH, so making it available for allocation.
		 The allocation event can be for any reason e.g. new call,
		 Handover and is represented by an 'ASSIGNMENT COMPLETE'
		 Message. These time segments are accumulated to give a
		 single total (GSM 04.08 [2])."
	    REFERENCE
		"Owner Module: RRM module
		 Mode-of-operation: set from RRM
		 Effective-time: immediately according current measurement interval"
	    ::= {cellMeasurmentPackage 17}

	meanTCHBusyTime	OBJECT-TYPE
	    SYNTAX	INTEGER
	    MAX-ACCESS	read-write
	    STATUS	current
	    DESCRIPTION
		"Mean TCH busy time:

		 This measurement provides the arithmetic mean of the busy
		 time for TCHs in a CELL, i.e. the time the channels have
		 been occupied.

		 This measurement is obtained by accumulating each TCHs busy
		 time. TCH is busy between an 'ASSIGNMENT COMPLETE' Message
		 and the complementary 'RELEASE' Message. All values are added
		 up and divided by the number of TCHs at the end of the
		 granularity period to obtain the arithmetic mean. (Further
		 information can be found in GSM 04.08 [2])."
	    REFERENCE
		"Owner Module: RRM module
		 Mode-of-operation: set from RRM
		 Effective-time: immediately according current measurement interval"
	    ::= {cellMeasurmentPackage 18}

	meanTCHQueueLength	OBJECT-TYPE
	    SYNTAX	INTEGER
	    MAX-ACCESS	read-write
	    STATUS	current
	    DESCRIPTION
		"Mean TCH queue length:

		 This measurement provides the arithmetic mean of the number
		 of queued TCH assignment procedures.

		 This measurement is obtained by sampling at a pre-defined
		 interval (System designed), the TCH queue length and then
		 taking the arithmetic mean (GSM 04.08 [2])."
	    REFERENCE
		"Owner Module: RRM module
		 Mode-of-operation: set from RRM
		 Effective-time: immediately according current measurement interval"
	    ::= {cellMeasurmentPackage 19}

	nbrOfLostRadioLinksTCH	OBJECT-TYPE
	    SYNTAX	INTEGER
	    MAX-ACCESS	read-write
	    STATUS	current
	    DESCRIPTION
		"Number of lost Radio links while using a TCH:

		 This measurement provides the number of calls terminated due
		 to RF failure on the radio path.


		 A local end release due to a 'RADIO LINK FAILURE' experienced
		 by the BTS when using a TCH (GSM 05.08 [4])."
	    REFERENCE
		"Owner Module: RRM module
		 Mode-of-operation: set from RRM
		 Effective-time: immediately according current measurement interval"
	    ::= {cellMeasurmentPackage 20}

	nbrOfAvailableSDCCHs	OBJECT-TYPE
	    SYNTAX	INTEGER
	    MAX-ACCESS	read-write
	    STATUS	current
	    DESCRIPTION
		"Number of Available SDCCHs:

		 This measurement provides the number of SDCCHs which are
		 available to be used (including those actually in use).

		 The gauge will be incremented when the SDCCH becomes
		 available and decremented when it becomes unavailable. The
		 SDCCH is available when its administrative state is 'unlocked'
		 or 'shuttingdown' and the operational state is 'enabled', and
		 is unavailable when its administrative state changes to
		 'locked' or operational state changes to 'disabled'. The
		 gauge value equals the number of SDCCHs with an administrative
		 state of 'unlocked' or 'shuttingdown' and an operational
		 state of 'enabled', (GSM 04.08 [2])."
	    REFERENCE
		"Owner Module: RRM module
		 Mode-of-operation: set from RRM
		 Effective-time: immediately according current measurement interval"
	    ::= {cellMeasurmentPackage 21}

	meanNbrOfBusySDCCHs	OBJECT-TYPE
	    SYNTAX	INTEGER
	    MAX-ACCESS	read-write
	    STATUS	current
	    DESCRIPTION
		"Mean number of busy SDCCHs:

		 This measurement provides the arithmetic mean of the number
		 of SDCCHs which are simultaneously in use.

		 This measurement is obtained by sampling at a pre-defined
		 interval (System designed), the SDCCHs which are busy and
		 then taking the arithmetic mean (GSM 04.08 [2])."
	    REFERENCE
		"Owner Module: RRM module
		 Mode-of-operation: set from RRM
		 Effective-time: immediately according current measurement interval"
	    ::= {cellMeasurmentPackage 22}

	maxNbrOfBusySDCCHs	OBJECT-TYPE
	    SYNTAX	INTEGER
	    MAX-ACCESS	read-write
	    STATUS	current
	    DESCRIPTION
		"Maximum number of busy SDCCHs:

		 This measurement provides the highest recorded value for
		 the number of SDCCHs simultaneously in use.

		 This measurement is obtained by sampling at a pre-defined
		 interval (System designed), the number of SDCCHs which are
		 'busy', and then taking the maximum of all such values at
		 the end of the granularity period, (GSM 04.08 [2])."
	    REFERENCE
		"Owner Module: RRM module
		 Mode-of-operation: set from RRM
		 Effective-time: immediately according current measurement interval"
	    ::= {cellMeasurmentPackage 23}

	attSDCCHSeizuresMeetingSDCCHBlockedState	OBJECT-TYPE
	    SYNTAX	INTEGER
	    MAX-ACCESS	read-write
	    STATUS	current
	    DESCRIPTION
		"Attempted SDCCH Seizures meeting an SDCCH blocked state:

		 This measurement provides the number of attempted SDCCH
		 seizures meeting all busy SDCCH state.

		 This value is updated upon receipt of 'CHANNEL REQUEST'
		 Message from the MS sent on the RACH meeting all SDCCH
		 busy state (GSM 04.08 [2])."
	    REFERENCE
		"Owner Module: RRM module
		 Mode-of-operation: set from RRM
		 Effective-time: immediately according current measurement interval"
	    ::= {cellMeasurmentPackage 24}

	allAvailableSDCCHAllocatedTime	OBJECT-TYPE
	    SYNTAX	INTEGER
	    MAX-ACCESS	read-write
	    STATUS	current
	    DESCRIPTION
		"All Available SDCCH Allocated Time:

		 This measurement provides the accumulated time during the
		 granularity period when all available SDCCHs are in use or
		 otherwise unavailable to be allocated.

		 This value is updated each time segment represents the
		 elapsed time from the last available SDCCH being allocated
		 to the next occurrence of a release of a SDCCH, so making
		 it available for allocation. The allocation event can be
		 for any reason e.g. new call, Handover, and is represented
		 by a SABM Message. These time segments are accumulated to
		 give a single total (GSM 04.08 [2])."
	    REFERENCE
		"Owner Module: RRM module
		 Mode-of-operation: set from RRM
		 Effective-time: immediately according current measurement interval"
	    ::= {cellMeasurmentPackage 25}

	meanSDCCHQueueLength	OBJECT-TYPE
	    SYNTAX	INTEGER
	    MAX-ACCESS	read-write
	    STATUS	current
	    DESCRIPTION
		"Mean SDCCH queue length:

		 This measurement provides the arithmetic mean of the number
		 of all messages waiting for transmission on the SDCCH.

		 This measurement is obtained by sampling at a pre-defined
		 interval (System designed), the SDCCH queue length and then
		 taking the arithmetic mean (GSM 04.08 [2])."
	    REFERENCE
		"Owner Module: RRM module
		 Mode-of-operation: set from RRM
		 Effective-time: immediately according current measurement interval"
	    ::= {cellMeasurmentPackage 26}

	nbrOfLostRadioLinksSDCCH	OBJECT-TYPE
	    SYNTAX	INTEGER
	    MAX-ACCESS	read-write
	    STATUS	current
	    DESCRIPTION
		"Number of lost Radio links while using an SDCCH:

		 This measurement provides the number of RF failure while
		 using the SDCCH.

		 A local end release, due to a 'RADIO LINK FAILURE',
		 experienced by the BTS when using an SDCCH (GSM 08.58 [6])."
	    REFERENCE
		"Owner Module: RRM module
		 Mode-of-operation: set from RRM
		 Effective-time: immediately according current measurement interval"
	    ::= {cellMeasurmentPackage 27}

	relativeTimeDLPowerControlAtMax	OBJECT-TYPE
	    SYNTAX	INTEGER
	    MAX-ACCESS	read-write
	    STATUS	current
	    DESCRIPTION
		"Relative time downlink power control at maximum:

		 This measurement provides the time downlink power control
		 was running at maximum level for the busy TCHs over the
		 measured period, relative to the total TCH busy time.

		 Each time segment represents the elapsed time when
		 BS_TXPWR_MAX is at maximum for each busy TCH. These time
		 segments are accumulated to give a single total. From this
		 information a value is derived such that it reflects a
		 percentage of the total channel busy time, (GSM 05.08 [4])."
	    REFERENCE
		"Owner Module: RRM module
		 Mode-of-operation: set from RRM
		 Effective-time: immediately according current measurement interval"
	    ::= {cellMeasurmentPackage 28}

	relativeTimeULPowerControlAtMax	OBJECT-TYPE
	    SYNTAX	INTEGER
	    MAX-ACCESS	read-write
	    STATUS	current
	    DESCRIPTION
		"Relative time uplink power control at maximum:

		 This measurement provides the time uplink power control
		 was running at maximum level for the seized TCHs over the
		 measured period, relative to the total TCH busy time.

		 Each time segment represents the elapsed time when
		 MS_TXPWR_MAX is at maximum for each busy TCH. These time
		 segments are accumulated to give a single total. From this
		 information a value is derived such that it reflects a
		 percentage of the total channel busy time, (GSM 05.08 [4])."
	    REFERENCE
		"Owner Module: RRM module
		 Mode-of-operation: set from RRM
		 Effective-time: immediately according current measurement interval"
	    ::= {cellMeasurmentPackage 29}

	succInternalHDOsIntraCell	OBJECT-TYPE
	    SYNTAX	INTEGER
	    MAX-ACCESS	read-write
	    STATUS	current
	    DESCRIPTION
		"Successful Internal Handovers, intra-CELL:

		 This measurement provides the number of times a call moves
		 from the occupied channel of the CELL to another free channel
		 of the same CELL.

		 Transmission of 'HANDOVER PERFORMED' Message to the MSC
		 (GSM 08.08 [5])."
	    REFERENCE
		"Owner Module: RRM module
		 Mode-of-operation: set from RRM
		 Effective-time: immediately according current measurement interval"
	    ::= {cellMeasurmentPackage 30}

	unsuccInternalHDOsIntraCell	OBJECT-TYPE
	    SYNTAX	INTEGER
	    MAX-ACCESS	read-write
	    STATUS	current
	    DESCRIPTION
		"Unsuccessful Internal Handovers, intra-CELL:

		 This measurement provides the number of unsuccessful intra
		 CELL Handovers, i.e. an attempt was made to move a call from
		 the occupied channel of the CELL to another free channel of
		 the same CELL.

		 This value is updated upon receipt of 'ASSIGNMENT FAILURE'
		 Message for the attempted handover (GSM 04.08 [2])."
	    REFERENCE
		"Owner Module: RRM module
		 Mode-of-operation: set from RRM
		 Effective-time: immediately according current measurement interval"
	    ::= {cellMeasurmentPackage 31}

--
--	The following 6 items are not needed for the Viper Cell BTS.
--
--	attIncomingInternalInterCellHDOs	OBJECT-TYPE
--	    SYNTAX	INTEGER
--	    MAX-ACCESS	read-write
--	    STATUS	current
--	    DESCRIPTION
--		"Attempted incoming Internal inter CELL Handovers:
--
--		 This measurement provides the number of attempted incoming
--		 Handovers into the observed CELL from the related adjacent
--		 CELLs controlled by the same BSC, further information can be
--		 found in GSM 04.08 [2], 08.08 [5] and 08.58 [6].
--
--		 An occurrence of a BSC internal event, depending on Handover
--		 algorithm."
--	    REFERENCE
--		"Owner Module: RRM module
--		 Mode-of-operation: set from RRM
--		 Effective-time: immediately according current measurement interval"
--	    ::= {cellMeasurmentPackage 32}
--
--	succIncomingInternalInterCellHDOs	OBJECT-TYPE
--	    SYNTAX	INTEGER
--	    MAX-ACCESS	read-write
--	    STATUS	current
--	    DESCRIPTION
--		"Successful incoming Internal inter CELL Handovers:
--
--		 This measurement provides the number of successful
--		 incoming Handovers into the observed CELL from the
--		 related adjacent CELLs controlled by the same BSC.
--
--		 Transmission of a 'HANDOVER PERFORMED' Message to the
--		 MSC (GSM 08.08 [5])."
--	    REFERENCE
--		"Owner Module: RRM module
--		 Mode-of-operation: set from RRM
--		 Effective-time: immediately according current measurement interval"
--	    ::= {cellMeasurmentPackage 33}
--
--	attOutgoingInternalInterCellHDOs	OBJECT-TYPE
--	    SYNTAX	INTEGER
--	    MAX-ACCESS	read-write
--	    STATUS	current
--	    DESCRIPTION
--		"Attempted outgoing Internal inter CELL Handovers:
--
--		 This measurement provides the number of attempted outgoing
--		 Handovers from the observed CELL to the related adjacent
--		 CELLs controlled by the same BSC.
--
--		Transmission of a 'HANDOVER COMMAND' Message (GSM 08.08 [5])."
--	    REFERENCE
--		"Owner Module: RRM module
--		 Mode-of-operation: set from RRM
--		 Effective-time: immediately according current measurement interval"
--	    ::= {cellMeasurmentPackage 34}
--
--	succOutgoingInternalInterCellHDOs	OBJECT-TYPE
--	    SYNTAX	INTEGER
--	    MAX-ACCESS	read-write
--	    STATUS	current
--	    DESCRIPTION
--		"Successful outgoing Internal inter CELL Handovers:
--
--		 This measurement provides the number of successful outgoing
--		 Handovers from the observed CELL to the related adjacent
--		 CELLs controlled by the same BSC.
--
--		 This value is updated upon transmission of a 'HANDOVER
--		 PERFORMED' Message to the MSC (GSM 08.08 [5])."
--	    REFERENCE
--		"Owner Module: RRM module
--		 Mode-of-operation: set from RRM
--		 Effective-time: immediately according current measurement interval"
--	    ::= {cellMeasurmentPackage 35}
--
--	unsuccHDOsWithReconnection	OBJECT-TYPE
--	    SYNTAX	INTEGER
--	    MAX-ACCESS	read-write
--	    STATUS	current
--	    DESCRIPTION
--		"Unsuccessful Internal Handovers with reconnection to old
--		 channels:
--
--		 This measurement provides the number of unsuccessful
--		 Handovers (with reconnection to the original channels),
--		 for the observed CELL.
--
--		 Receipt of 'HANDOVER FAILURE' Message received for the
--		 attempted handover (GSM 04.08 [2])."
--	    REFERENCE
--		"Owner Module: RRM module
--		 Mode-of-operation: set from RRM
--		 Effective-time: immediately according current measurement interval"
--	    ::= {cellMeasurmentPackage 36}
--
--	unsuccHDOsWithLossOfConnection	OBJECT-TYPE
--	    SYNTAX	INTEGER
--	    MAX-ACCESS	read-write
--	    STATUS	current
--	    DESCRIPTION
--		"Unsuccessful Internal Handovers with loss of connection:
--
--		 This measurement provides the number of unsuccessful
--		 Handovers that end in loosing the speech channel, for the
--		 observed CELL.
--
--		 Expiry of timer T3103 for Inter CELL Handovers and Expiry
--		 of timer T3107 for Intra CELL Handovers (GSM 04.08 [2])."
--	    REFERENCE
--		"Owner Module: RRM module
--		 Mode-of-operation: set from RRM
--		 Effective-time: immediately according current measurement interval"
--	    ::= {cellMeasurmentPackage 37}
--
callControlMeasurmentPackage OBJECT IDENTIFIER
-- 	DESCRIPTION
-- 		"Call Control (MSC) related measurments"
	::= {gp10GsmMib 13}

	nbrOfClassMarkUpdates	OBJECT-TYPE
	    SYNTAX	INTEGER
	    MAX-ACCESS	read-write
	    STATUS	current
	    DESCRIPTION
		"Number of class mark updates. This measurement provides
		 the number of classmark updates received from the BSS at
		 the MSC.

		 This value is updated upon receipt of 'CLASSMARK  UPDATE'
		 Message (GSM 08.08 [5])."
	    REFERENCE
		"Owner Module: CC module
		 Mode-of-operation: set from CC
		 Effective-time: update immediately according to measurement interval"
	    ::= {callControlMeasurmentPackage 1}

	attMobileOriginatingCalls	OBJECT-TYPE
	    SYNTAX	INTEGER
	    MAX-ACCESS	read-write
	    STATUS	current
	    DESCRIPTION
		"Attempted mobile originating calls. This measurement
		 provides the number of call attempts for mobile originating
		 traffic.

		 This value is updated upon receipt of 'CM_SERV_REQ' Message
		 from the originating MS, with service type set to originating
		 call establishment (GSM 04.08 [2])."
	    REFERENCE
		"Owner Module: CC module
		 Mode-of-operation: set from CC
		 Effective-time: update immediately according to measurement interval"
	    ::= {callControlMeasurmentPackage 2}

	succMobileOriginatingCalls	OBJECT-TYPE
	    SYNTAX	INTEGER
	    MAX-ACCESS	read-write
	    STATUS	current
	    DESCRIPTION
		"Successful mobile originating calls. This measurement
		 provides the number of successful calls for mobile
		 originating traffic.

		 This value is updated upon receipt of 'ASSIGNMENT COMPLETE'
		 Message from the originating MS, for the requested mobile
		 originating call (GSM 08.08 [5]). Note, the 'ALERTING'
		 Message from GSM 04.08 [2] is not used as the implementation
		 of it is optional."
	    REFERENCE
		"Owner Module: CC module
		 Mode-of-operation: set from CC
		 Effective-time: update immediately according to measurement interval"
	    ::= {callControlMeasurmentPackage 3}

	ansMobileOriginatingCalls	OBJECT-TYPE
	    SYNTAX	INTEGER
	    MAX-ACCESS	read-write
	    STATUS	current
	    DESCRIPTION
		"Answered mobile originating calls. This measurement
		 provides the number of answered calls for mobile
		 originating traffic.

		 This value is updated upon receipt of 'CONNECT ACKNOWLEDGE'
		 Message from the originating MS, for the requested mobile
		 originating call (GSM 04.08 [2])."
	    REFERENCE
		"Owner Module: CC module
		 Mode-of-operation: set from CC
		 Effective-time: update immediately according to measurement interval"
	    ::= {callControlMeasurmentPackage 4}

	attMobileTerminatingCalls	OBJECT-TYPE
	    SYNTAX	INTEGER
	    MAX-ACCESS	read-write
	    STATUS	current
	    DESCRIPTION
		"Attempted mobile terminating calls. This measurement
		 provides the number of call attempts for mobile
		 terminating traffic.

		 This vvalue is updated upon transmission of 'SETUP'
		 Message to the called MS, for the requested mobile
		 terminating call (GSM 04.08 [2])."
	    REFERENCE
		"Owner Module: CC module
		 Mode-of-operation: set from CC
		 Effective-time: update immediately according to measurement interval"
	    ::= {callControlMeasurmentPackage 5}

	succMobileTerminatingCalls	OBJECT-TYPE
	    SYNTAX	INTEGER
	    MAX-ACCESS	read-write
	    STATUS	current
	    DESCRIPTION
		"Successful mobile terminating calls. This measurement
		 provides the number of successful calls for mobile
		 terminating traffic.

		 This value is updated upon receipt of 'ASSIGNMENT COMPLETE'
		 Message from the called MS, for the requested mobile
		 terminating call (GSM 08.08 [5]). Note, the 'ALERTING'
		 Message from GSM 04.08 [2] is not used as the implementation
		 of it is optional."
	    REFERENCE
		"Owner Module: CC module
		 Mode-of-operation: set from CC
		 Effective-time: update immediately according to measurement interval"
	    ::= {callControlMeasurmentPackage 6}

	ansMobileTerminatingCalls	OBJECT-TYPE
	    SYNTAX	INTEGER
	    MAX-ACCESS	read-write
	    STATUS	current
	    DESCRIPTION
		"Answered mobile terminating calls. This measurement
		 provides the number of answered calls for mobile
		 terminating traffic.

		 This value is updated upon transmission of 'CONNECTION
		 ACKNOWLEDGE' Message to the called MS, for the requested
		 mobile terminating call (GSM 04.08 [2])."
	    REFERENCE
		"Owner Module: CC module
		 Mode-of-operation: set from CC
		 Effective-time: update immediately according to measurement interval"
	    ::= {callControlMeasurmentPackage 7}

	attMobileEmergencyCalls	OBJECT-TYPE
	    SYNTAX	INTEGER
	    MAX-ACCESS	read-write
	    STATUS	current
	    DESCRIPTION
		"Attempted Mobile Emergency calls. This measurement
		 provides the number of emergency call attempts.

		 This value is updated upon receipt of 'CM_SERV_REQ'
		 Message from the originating MS, with service indicator
		 set to emergency call (GSM 04.08 [2])."
	    REFERENCE
		"Owner Module: CC module
		 Mode-of-operation: set from CC
		 Effective-time: update immediately according to measurement interval"
	    ::= {callControlMeasurmentPackage 8}

	succMobileEmergencyCalls	OBJECT-TYPE
	    SYNTAX	INTEGER
	    MAX-ACCESS	read-write
	    STATUS	current
	    DESCRIPTION
		"Successful Mobile Emergency calls. This measurement provides
		 the number of successful emergency calls.

		 this value is updated upon receipt of 'ASSIGNMENT COMPLETE'
		 Message from the originating MS, for the requested emergency
		 call (GSM 08.08 [5]). Note, the 'ALERTING' Message from
		 GSM 04.08 [2] is not used as the implementation of it
		 is optional."
	    REFERENCE
		"Owner Module: CC module
		 Mode-of-operation: set from CC
		 Effective-time: update immediately according to measurement interval"
	    ::= {callControlMeasurmentPackage 9}

	ansMobileEmergencyCalls	OBJECT-TYPE
	    SYNTAX	INTEGER
	    MAX-ACCESS	read-write
	    STATUS	current
	    DESCRIPTION
		"Answered Mobile Emergency calls. This measurement provides
		 the number of answered emergency calls.

		 This value is updated upon receipt of 'CONNECTION ACKNOWLEDGE'
		 Message from the originating MS, for the requested emergency
		 call (GSM 04.08 [2])."
	    REFERENCE
		"Owner Module: CC module
		 Mode-of-operation: set from CC
		 Effective-time: update immediately according to measurement interval"
	    ::= {callControlMeasurmentPackage 10}

	attCipheringModeControlProcs	OBJECT-TYPE
	    SYNTAX	INTEGER
	    MAX-ACCESS	read-write
	    STATUS	current
	    DESCRIPTION
		"Attempted ciphering mode control procedures. This measurement
		 provides the number of ciphering mode control procedures
		 transmitted (these are counted as attempts).

		 This value is updated upon transmission of 'CIPHER MODE
		 COMMAND' (GSM 08.08 [5])."
	    REFERENCE
		"Owner Module: CC module
		 Mode-of-operation: set from CC
		 Effective-time: update immediately according to measurement interval"
	    ::= {callControlMeasurmentPackage 11}

	succCipheringModeControlProcs	OBJECT-TYPE
	    SYNTAX	INTEGER
	    MAX-ACCESS	read-write
	    STATUS	current
	    DESCRIPTION
		"Successful ciphering mode control procedures. This
		 measurement provides the number of successful ciphering
		 mode control procedures.

		 Receipt of 'CIPHER MODE COMPLETE' Message (GSM 08.08 [5])."
	    REFERENCE
		"Owner Module: CC module
		 Mode-of-operation: set from CC
		 Effective-time: update immediately according to measurement interval"
	    ::= {callControlMeasurmentPackage 12}

	attInterrogationOfHLRsForRouting	OBJECT-TYPE
	    SYNTAX	INTEGER
	    MAX-ACCESS	read-write
	    STATUS	current
	    DESCRIPTION
		"Attempted interrogations of HLRs for routing. This
		 measurement provides the number of HLR interrogations
		 by the GMSC with the purpose of routing incoming calls
		 (these are counted as attempts).

		 This value is updated upon transmission of a 
		 'MAP_SEND_ROUTING_INFORMATION' service request
		 (GSM 09.02 [7])."
	    REFERENCE
		"Owner Module: GUDB module
		 Mode-of-operation: set from GUDB
		 Effective-time: update immediately according to measurement interval"
	    ::= {callControlMeasurmentPackage 13}

	succInterrogationOfHLRsMSRNObtained	OBJECT-TYPE
	    SYNTAX	INTEGER
	    MAX-ACCESS	read-write
	    STATUS	current
	    DESCRIPTION
		"Successful interrogations of HLR (MSRN obtained). This
		 measurement provides the number of successful HLR
		 interrogations, where MSRN is obtained.

		 This value is updated upon receipt of
		 'MAP_SEND_ROUTING_INFORMATION' service confirmation
		 containing a 'MSRN' parameter value (GSM 09.02 [7])."
	    REFERENCE
		"Owner Module: GUDB module
		 Mode-of-operation: set from GUDB
		 Effective-time: update immediately according to measurement interval"
	    ::= {callControlMeasurmentPackage 14}

	succInterrogationOfHLRsCallForwarding	OBJECT-TYPE
	    SYNTAX	INTEGER
	    MAX-ACCESS	read-write
	    STATUS	current
	    DESCRIPTION
		"Successful interrogations of HLR (call Forwarding). This
		 measurement provides the number of successful HLR
		 interrogations, by the GMSC for call forwarding.

		 This value is updated upon receipt of
		 'MAP_SEND_ROUTING_INFORMATION' service confirmation
		 containing a 'Forwarding Data' parameter value (GSM09.02[7])."
	    REFERENCE
		"Owner Module: GUDB module
		 Mode-of-operation: set from GUDB
		 Effective-time: update immediately according to measurement interval"
	    ::= {callControlMeasurmentPackage 15}

	attOpForMobileOriginatingPointToPointSMs	OBJECT-TYPE
	    SYNTAX	INTEGER
	    MAX-ACCESS	read-write
	    STATUS	current
	    DESCRIPTION
		"Attempted operations for mobile originating point to point SMs
		 This measurement provides the number of operations for
		 mobile originating point to point short messages (these are
		 counted as attempts).

		 This value is updated upon receipt of 'RP-DATA' Message
		 (GSM 04.11 [3])."
	    REFERENCE
		"Owner Module: SMS module
		 Mode-of-operation: set from SMS
		 Effective-time: update immediately according to measurement interval"
	    ::= {callControlMeasurmentPackage 16}

	succOpForMobileOriginatingPointToPointSMs	OBJECT-TYPE
	    SYNTAX	INTEGER
	    MAX-ACCESS	read-write
	    STATUS	current
	    DESCRIPTION
		"Successful operations for mobile originating point to
		 point SMs. This measurement provides the number of
		 successful operations for mobile originating point to
		 point short messages.

		 This value is updated upon transmission of 'RP-ACK'
		 Message (GSM 04.11 [3])."
	    REFERENCE
		"Owner Module: SMS module
		 Mode-of-operation: set from SMS
		 Effective-time: update immediately according to measurement interval"
	    ::= {callControlMeasurmentPackage 17}

	attOpForMobileTerminatingPointToPointSMs	OBJECT-TYPE
	    SYNTAX	INTEGER
	    MAX-ACCESS	read-write
	    STATUS	current
	    DESCRIPTION
		"Attempted operations for mobile terminating point to
		 point SMs. This measurement provides the number of
		 operations for mobile terminating point to point short
		 messages (these are counted as attempts).

		 This value is updated upon transmission of 'RP-DATA'
		 Message (GSM 04.11 [3])."
	    REFERENCE
		"Owner Module: SMS module
		 Mode-of-operation: set from SMS
		 Effective-time: update immediately according to measurement interval"
	    ::= {callControlMeasurmentPackage 18}

	succOpForMobileTerminatingPointToPointSMs	OBJECT-TYPE
	    SYNTAX	INTEGER
	    MAX-ACCESS	read-write
	    STATUS	current
	    DESCRIPTION
		"Successful operations for mobile terminating point to
		 point SMs. This measurement provides the number of
		 successful operations for mobile terminating point to
		 point short messages.

		 This value is updated upon receipt of 'RP-ACK' Message
		 (GSM 04.11 [3])."
	    REFERENCE
		"Owner Module: SMS module
		 Mode-of-operation: set from SMS
		 Effective-time: update immediately according to measurement interval"
	    ::= {callControlMeasurmentPackage 19}

	meanTimeToCallSetupService	OBJECT-TYPE
	    SYNTAX	INTEGER
	    MAX-ACCESS	read-write
	    STATUS	current
	    DESCRIPTION
		"Mean time to provide the CALL SETUP service. This
		 measurement provides the arithmetic mean of the time
		 to provide the CALL SETUP service to a requesting MS.

		 This measurement is obtained by accumulating the time
		 intervals between 'SETUP' and the corresponding 'ASSIGNMENT
		 COMPLETE' messages over a granularity period using DER. This
		 end value of the time will then be divided by the number of
		 call set-ups observed in the granularity period to give the
		 arithmetic mean (GSM 04.08 [2], GSM 08.08 [5])."
	    REFERENCE
		"Owner Module: CC module
		 Mode-of-operation: set from CC
		 Effective-time: update immediately according to measurement interval"
	    ::= {callControlMeasurmentPackage 20}


	meanTimeToLocationUpdateService	OBJECT-TYPE
	    SYNTAX	INTEGER
	    MAX-ACCESS	read-write
	    STATUS	current
	    DESCRIPTION
		"Mean time to provide the LOCATION UPDATING service. This
		 measurement provides the arithmetic mean of the time to
		 provide the LOCATION UPDATING service to an MS changing
		 Location area.

		 This measurement is obtained by accumulating the time
		 interval between 'LOCATION UPDATE REQUEST' and the
		 corresponding 'LOCATION UPDATING ACCEPT' Message over
		 a granularity period using DER. This end value of the
		 time will then be divided by number of Location Update
		 requests observed in the granularity period to give the
		 arithmetic mean (GSM 04.08 [2])."
	    REFERENCE
		"Owner Module: MM module
		 Mode-of-operation: set from MM
		 Effective-time: update immediately according to measurement interval"
	    ::= {callControlMeasurmentPackage 21}

	transSubIdentifiedWithIMSI	OBJECT-TYPE
	    SYNTAX	INTEGER
	    MAX-ACCESS	read-write
	    STATUS	current
	    DESCRIPTION
		"Transactions on the MM-layer where subscriber was identified
		 with IMSI. This measurement provides the number of
		 transactions on the MM-layer where the mobile subscriber
		 was identified with his IMSI.

		 This value is updated when any MM-layer transaction which
		 causes the MS to be identified with his IMSI (GSM 04.08 [2]),
		 i.e. CM_Re-establishment, CM_Service request, Identity
		 response, IMSI detach indication, Location updating accept,
		 Location updating request, TMSI re-allocation command."
	    REFERENCE
		"Owner Module: MM module
		 Mode-of-operation: set from MM
		 Effective-time: update immediately according to measurement interval"
	    ::= {callControlMeasurmentPackage 22}

	imsiDetachProcs	OBJECT-TYPE
	    SYNTAX	INTEGER
	    MAX-ACCESS	read-write
	    STATUS	current
	    DESCRIPTION
		"IMSI detach procedures. This measurement provides the
		 number of IMSI procedures that involve a detach within
		 one MSC area, (see BSC Measurement Function for IMSI
		 attach procedures)

		 This value is updated upon receipt of 'IMSI DETACH
		 INDICATION' Message from the MS (GSM 04.08 [2])."
	    REFERENCE
		"Owner Module: MM module
		 Mode-of-operation: set from MM
		 Effective-time: update immediately according to measurement interval"
	    ::= {callControlMeasurmentPackage 23}

	imsiAttachProcs	OBJECT-TYPE
	    SYNTAX	INTEGER
	    MAX-ACCESS	read-write
	    STATUS	current
	    DESCRIPTION
		"IMSI attach procedures. This measurement provides the
		 number of IMSI procedures that involve an attach within
		 one MSC area.

		 This value is updated upon receipt of 'LOCATION UPDATING
		 REQUEST' Message from the MS, indicating an IMSI attach,
		 (GSM 04.08 [2]) (see MSC Measurement Function for IMSI
		 detach procedures)."
	    REFERENCE
		"Owner Module: MM module
		 Mode-of-operation: set from MM
		 Effective-time: update immediately according to measurement interval"
	    ::= {callControlMeasurmentPackage 24}

	attIncomingInterMSCHDOs	OBJECT-TYPE
	    SYNTAX	INTEGER
	    MAX-ACCESS	read-write
	    STATUS	current
	    DESCRIPTION
		"Attempted incoming inter-MSC Handovers. This measurement
		 provides the number of attempted incoming Handovers into
		 the observed CELL from the related adjacent CELLs NOT
		 controlled by this MSC.

		 This value is updated upon receipt of a 'MAP_PERFORM_HANDOVER'
		 service indication with target CELL identity equal to the
		 observed CELL (GSM 09.02 [7])."
	    REFERENCE
		"Owner Module: HO-signaling module
		 Mode-of-operation: set from HO-signaling
		 Effective-time: update immediately according to measurement interval"
	    ::= {callControlMeasurmentPackage 25}

	succIncomingInterMSCHDOs	OBJECT-TYPE
	    SYNTAX	INTEGER
	    MAX-ACCESS	read-write
	    STATUS	current
	    DESCRIPTION
		"Successful incoming inter-MSC Handovers. This measurement
		 provides the number of successful incoming Handovers into
		 the observed CELL from the related adjacent CELLs NOT
		 controlled by this MSC.

		 This value is updated upon receipt of a 'MAP_SEND_END_SIGNAL'
		 service confirmation (GSM 09.02 [7])."
	    REFERENCE
		"Owner Module: HO-signaling module
		 Mode-of-operation: set from HO-signaling
		 Effective-time: update immediately according to measurement interval"
	    ::= {callControlMeasurmentPackage 26}


	attOutgoingInterMSCHDOs	OBJECT-TYPE
	    SYNTAX	INTEGER
	    MAX-ACCESS	read-write
	    STATUS	current
	    DESCRIPTION
		"Attempted outgoing inter-MSC Handovers. This measurement
		 provides the number of attempted outgoing Handovers from
		 the observed CELL to the related adjacent CELLs NOT
		 controlled by this MSC.

		 This value is updated upon transmission of a
		 'MAP_PERFORM_HANDOVER' service request (GSM 09.02 [7])."
	    REFERENCE
		"Owner Module: HO-signaling module
		 Mode-of-operation: set from HO-signaling
		 Effective-time: update immediately according to measurement interval"
	    ::= {callControlMeasurmentPackage 27}


	succOutgoingInterMSCHDOs	OBJECT-TYPE
	    SYNTAX	INTEGER
	    MAX-ACCESS	read-write
	    STATUS	current
	    DESCRIPTION
		"Successful outgoing inter-MSC Handovers. This measurement
		 provides the number of successful outgoing Handovers from
		 the observed CELL to the related adjacent CELLs NOT
		 controlled by this MSC.

		 This value is updated upon transmission of
		 'MAP_SEND_END_SIGNAL' service response (GSM 09.02 [7])."
	    REFERENCE
		"Owner Module: HO-signaling module
		 Mode-of-operation: set from HO-signaling
		 Effective-time: update immediately according to measurement interval"
	    ::= {callControlMeasurmentPackage 28}

	externalHDOsPerCauseTable	OBJECT-TYPE
	    SYNTAX	SEQUENCE OF ExternalHDOsPerCauseEntry
	    MAX-ACCESS	not-accessible
	    STATUS	current
	    DESCRIPTION
		"This entry is required to define a table of values."
	    REFERENCE
		"Owner Module: HO-signaling + CC module
		 Mode-of-operation: set from HO-signaling or CC-module
		 Effective-time: update immediately according to measurement interval"
	    ::= {callControlMeasurmentPackage 29}

	externalHDOsPerCauseEntry	OBJECT-TYPE
	    SYNTAX	ExternalHDOsPerCauseEntry
	    MAX-ACCESS	not-accessible
	    STATUS	current
	    DESCRIPTION
		"External Handovers per cause. This measurement provides
		 the number of attempted MSC controlled Handovers, per cause.

		 These values are updated upon receipt of a 'HANDOVER REQUIRED'
		 Message (GSM 08.08 [5])."
	    REFERENCE
		"Owner Module: HO-signaling + CC module
		 Mode-of-operation: set from HO-signaling or CC-module
		 Effective-time: update immediately according to measurement interval"
	    INDEX	{externalHDOsPerCauseCode}
	    --DEFAULT cookie MIBT_%n
	    ::= {externalHDOsPerCauseTable 1}

	ExternalHDOsPerCauseEntry	::= SEQUENCE {
	    externalHDOsPerCauseCode		CauseCode,
	    externalHDOsPerCauseValue		INTEGER
	}

	externalHDOsPerCauseCode	OBJECT-TYPE
	    SYNTAX	CauseCode
	    MAX-ACCESS	read-only
	    STATUS	current
	    DESCRIPTION
		"Cause of the external handover."
	    REFERENCE
		"Owner Module: HO-signaling + CC module
		 Mode-of-operation: set from HO-signaling or CC-module
		 Effective-time: update immediately according to measurement interval"
	    ::= {externalHDOsPerCauseEntry 1}

	externalHDOsPerCauseValue	OBJECT-TYPE
	    SYNTAX	INTEGER
	    MAX-ACCESS	read-write
	    STATUS	current
	    DESCRIPTION
		"Counter of the number of external handovers for this cause."
	    REFERENCE
		"Owner Module: HO-signaling + CC module
		 Mode-of-operation: set from HO-signaling or CC-module
		 Effective-time: update immediately according to measurement interval"
	    ::= {externalHDOsPerCauseEntry 2}

	unsuccExternHDOsWithReconnectionPerMSC	OBJECT-TYPE
	    SYNTAX	INTEGER
	    MAX-ACCESS	read-write
	    STATUS	current
	    DESCRIPTION
		"Unsuccessful External Handovers with reconnection to old
		 channels, per MSC. This measurement provides the number of
		 unsuccessful Handovers with reconnection to the original
		 channels (TCH & SDCCH), on a per MSC basis.

		 This value is updated upon receipt of: 'HANDOVER FAILURE'
		 Message for the attempted handover (GSM 08.08 [5]).

		 Note: the 'per MSC' would indicate a table, but in the
		 specs this is defined as a single value."
	    REFERENCE
		"Owner Module: HO-signaling + CC module
		 Mode-of-operation: set from HO-signaling or CC-module
		 Effective-time: update immediately according to measurement interval"
	    ::= {callControlMeasurmentPackage 30}

	unsuccExternHDOsWithLossOfConnectionPerMSC	OBJECT-TYPE
	    SYNTAX	INTEGER
	    MAX-ACCESS	read-write
	    STATUS	current
	    DESCRIPTION
		"Unsuccessful External Handovers with loss of connection,
		 per MSC. This measurement provides the number of unsuccessful
		 Handovers, with loss of the call, on a per MSC basis.

		 This value is updated pon receipt of 'CLEAR REQUEST'
		 Message for the requested Handover (GSM 08.08 [5]).

		 Note: the 'per MSC' would indicate a table, but in the
		 specs this is defined as a single value."
	    REFERENCE
		"Owner Module: HO-signaling + CC module
		 Mode-of-operation: set from HO-signaling or CC-module
		 Effective-time: update immediately according to measurement interval"
	    ::= {callControlMeasurmentPackage 31}
	    
--
--	ViperCell H323 MIB informaiton
--

	h323-GKPort	OBJECT-TYPE
	    SYNTAX	INTEGER
	    MAX-ACCESS	read-write
	    STATUS	current
	    DESCRIPTION
		"Gate Keeper's listning port"
	    DEFVAL
		{1720}
	    ::= {gp10H323Mib 1}

	h323-GKIPAddress	OBJECT-TYPE
	    SYNTAX	IpAddress
	    MAX-ACCESS	read-write
	    STATUS	current
	    DESCRIPTION
		"Gate Keeper's IP Address"
	    ::= {gp10H323Mib 2}

	h323-Q931ResponseTimeOut	OBJECT-TYPE
	    SYNTAX	INTEGER
	    MAX-ACCESS	read-write
	    STATUS	current
	    DESCRIPTION
		"Q931 Response Time Out"
	    DEFVAL
		{100}
	    ::= {gp10H323Mib 3}

	h323-Q931ConnectTimeOut	OBJECT-TYPE
	    SYNTAX	INTEGER
	    MAX-ACCESS	read-write
	    STATUS	current
	    DESCRIPTION
		"Q931 Connect time out"
	    DEFVAL
		{150}
	    ::= {gp10H323Mib 4}

	h323-Q931CallSignalingPort	OBJECT-TYPE
	    SYNTAX	INTEGER
	    MAX-ACCESS	read-write
	    STATUS	current
	    DESCRIPTION
		"Q931 Call Singaling Port"
	    DEFVAL
		{500}
	    ::= {gp10H323Mib 5}

	h323-t35CountryCode	OBJECT-TYPE
	    SYNTAX	INTEGER
	    MAX-ACCESS	read-write
	    STATUS	current
	    DESCRIPTION
		"t35 Country Code"
	    DEFVAL
		{0}
	    ::= {gp10H323Mib 6}

	h323-rasRequestTimeout	OBJECT-TYPE
	    SYNTAX	INTEGER
	    MAX-ACCESS	read-write
	    STATUS	current
	    DESCRIPTION
		"RAS Request Timeout"
	    DEFVAL
		{0}
	    ::= {gp10H323Mib 7}

	h323-viperbaseHeartbeatTimeout	OBJECT-TYPE
	    SYNTAX	INTEGER
	    MAX-ACCESS	read-write
	    STATUS	current
	    DESCRIPTION
		"Viperbase Heartbeat Timeout"
	    DEFVAL
		{0}
	    ::= {gp10H323Mib 8}

--
--	ViperCell Configuration Information
--

callConfigData OBJECT IDENTIFIER
-- 	DESCRIPTION
--		"Call Control Configuration Data"
	::= {gp10ConfigMib 1}

	cc-max-L3-msgs	OBJECT-TYPE
	    SYNTAX	INTEGER
	    MAX-ACCESS	read-write
	    STATUS	current
	    DESCRIPTION
		"Maximum number of silmultaneous messages"
	    DEFVAL
		{32}
	    ::= {callConfigData 1}

	cc-l3-msg-q-priority	OBJECT-TYPE
	    SYNTAX	INTEGER
	    MAX-ACCESS	read-write
	    STATUS	current
	    DESCRIPTION
		"VxWorks priority for the msg Q."
	    DEFVAL
		{10}
	    ::= {callConfigData 2}

	cc-task-priority	OBJECT-TYPE
	    SYNTAX	INTEGER
	    MAX-ACCESS	read-write
	    STATUS	current
	    DESCRIPTION
		"Call Control Task Priority."
	    DEFVAL
		{100}
	    ::= {callConfigData 3}

	cc-task-stack-size	OBJECT-TYPE
	    SYNTAX	INTEGER
	    MAX-ACCESS	read-write
	    STATUS	current
	    DESCRIPTION
		"Task stack size."
	    DEFVAL
		{10000}
	    ::= {callConfigData 4}

	cc-mm-conn-est-T999	OBJECT-TYPE
	    SYNTAX	INTEGER
	    MAX-ACCESS	read-write
	    STATUS	current
	    DESCRIPTION
		"MM Connection Established."
	    DEFVAL
		{2000}
	    ::= {callConfigData 5}

	cc-alerting-T301	OBJECT-TYPE
	    SYNTAX	INTEGER
	    MAX-ACCESS	read-write
	    STATUS	current
	    DESCRIPTION
		"Alerting received Timer."
	    DEFVAL
		{2000}
	    ::= {callConfigData 6}

	cc-setup-T303	OBJECT-TYPE
	    SYNTAX	INTEGER
	    MAX-ACCESS	read-write
	    STATUS	current
	    DESCRIPTION
		"Setup sent."
	    DEFVAL
		{2000}
	    ::= {callConfigData 7}

	cc-call-confirmed-T310	OBJECT-TYPE
	    SYNTAX	INTEGER
	    MAX-ACCESS	read-write
	    STATUS	current
	    DESCRIPTION
		"Call Confirmed received Timer."
	    DEFVAL
		{2000}
	    ::= {callConfigData 8}

	cc-connect-T313	OBJECT-TYPE
	    SYNTAX	INTEGER
	    MAX-ACCESS	read-write
	    STATUS	current
	    DESCRIPTION
		"Connect sent Timer."
	    DEFVAL
		{2000}
	    ::= {callConfigData 9}

	cc-disconnect-T305	OBJECT-TYPE
	    SYNTAX	INTEGER
	    MAX-ACCESS	read-write
	    STATUS	current
	    DESCRIPTION
		"Disconnect sent Timer."
	    DEFVAL
		{2000}
	    ::= {callConfigData 10}

	cc-release-T308	OBJECT-TYPE
	    SYNTAX	INTEGER
	    MAX-ACCESS	read-write
	    STATUS	current
	    DESCRIPTION
		"Release sent Timer."
	    DEFVAL
		{2000}
	    ::= {callConfigData 11}

	cc-safety-timer	OBJECT-TYPE
	    SYNTAX	INTEGER
	    MAX-ACCESS	read-write
	    STATUS	current
	    DESCRIPTION
		"Call Task running too long."
	    DEFVAL
		{1000}
	    ::= {callConfigData 12}

	cc-max-calls	OBJECT-TYPE
	    SYNTAX	INTEGER
	    MAX-ACCESS	read-write
	    STATUS	current
	    DESCRIPTION
		"Maximum # of Calls allowed."
	    DEFVAL
		{7}
	    ::= {callConfigData 13}

mobilityConfigData OBJECT IDENTIFIER
-- 	DESCRIPTION
--		"Mobility Management Configuration Data"
	::= {gp10ConfigMib 2}

	mm-max-mm-connections	OBJECT-TYPE
	    SYNTAX	INTEGER
	    MAX-ACCESS	read-write
	    STATUS	current
	    DESCRIPTION
		"Maximum number of MM Connections allowed."
	    DEFVAL
		{10}
	    ::= {mobilityConfigData 1}

	mm-max-L3-msgs	OBJECT-TYPE
	    SYNTAX	INTEGER
	    MAX-ACCESS	read-write
	    STATUS	current
	    DESCRIPTION
		"Defines the size of VxWorks Message queue
		 The value of this parameter is system dependent"
	    DEFVAL
		{32}
	    ::= {mobilityConfigData 2}

	task-priority	OBJECT-TYPE
	    SYNTAX	INTEGER
	    MAX-ACCESS	read-write
	    STATUS	current
	    DESCRIPTION
		"Mobility Management Task Priority."
	    DEFVAL
		{100}
	    ::= {mobilityConfigData 3}

	task-stack-size	OBJECT-TYPE
	    SYNTAX	INTEGER
	    MAX-ACCESS	read-write
	    STATUS	current
	    DESCRIPTION
		"Task stack size."
	    DEFVAL
		{20000}
	    ::= {mobilityConfigData 4}

	mm-paging-t3113	OBJECT-TYPE
	    SYNTAX	INTEGER
	    MAX-ACCESS	read-write
	    STATUS	current
	    DESCRIPTION
		"Paging Response Timer - Network"
	    DEFVAL
		{3000}
	    ::= {mobilityConfigData 5}

	mm-authenticationRequired	OBJECT-TYPE
	    SYNTAX	Boolean
	    MAX-ACCESS	read-write
	    STATUS	current
	    DESCRIPTION
		"Authentication Required."
	    DEFVAL
		{false}
	    ::= {mobilityConfigData 6}

	mm-cipheringRequired	OBJECT-TYPE
	    SYNTAX	Boolean
	    MAX-ACCESS	read-write
	    STATUS	current
	    DESCRIPTION
		"CipheringRequired"
	    DEFVAL
		{false}
	    ::= {mobilityConfigData 7}

	mm-IMEICheckRequired	OBJECT-TYPE
	    SYNTAX	Boolean
	    MAX-ACCESS	read-write
	    STATUS	current
	    DESCRIPTION
		"Mobility Confirmed received Timer."
	    DEFVAL
		{false}
	    ::= {mobilityConfigData 8}

resourceConfigData OBJECT IDENTIFIER
-- 	DESCRIPTION
--		"Resource Management Configuration Data"
	::= {gp10ConfigMib 3}

	rm-t3L01	OBJECT-TYPE
	    SYNTAX	INTEGER
	    MAX-ACCESS	read-write
	    STATUS	current
	    DESCRIPTION
		"Currently Unused"
	    DEFVAL
		{0}
	    ::= {resourceConfigData 1}

	rm-bsCcChans	OBJECT-TYPE
	    SYNTAX	INTEGER
	    MAX-ACCESS	read-write
	    STATUS	current
	    DESCRIPTION
		"Currently Unused"
	    DEFVAL
		{0}
	    ::= {resourceConfigData 2}

	rm-bsCcchSdcchComb	OBJECT-TYPE
	    SYNTAX	INTEGER
	    MAX-ACCESS	read-write
	    STATUS	current
	    DESCRIPTION
		"Currently Unused"
	    DEFVAL
		{0}
	    ::= {resourceConfigData 3}

	rm-sysInfoOnOffMap	OBJECT-TYPE
	    SYNTAX	INTEGER
	    MAX-ACCESS	read-write
	    STATUS	current
	    DESCRIPTION
		"Currently Unused"
	    DEFVAL
		{0}
	    ::= {resourceConfigData 4}

	rm-airInterface	OBJECT-TYPE
	    SYNTAX	INTEGER
	    MAX-ACCESS	read-write
	    STATUS	current
	    DESCRIPTION
		"Radio system in use e.g. GSM900, DCS1800, PCS1900, etc."
	    DEFVAL
		{0}
	    ::= {resourceConfigData 5}

	rm-viperCellTsc	OBJECT-TYPE
	    SYNTAX	INTEGER
	    MAX-ACCESS	read-write
	    STATUS	current
	    DESCRIPTION
		"Currently Unused"
	    DEFVAL
		{0}
	    ::= {resourceConfigData 6}

	rm-maxSlotPerTrx	OBJECT-TYPE
	    SYNTAX	INTEGER
	    MAX-ACCESS	read-write
	    STATUS	current
	    DESCRIPTION
		"Currently Unused"
	    DEFVAL
		{0}
	    ::= {resourceConfigData 7}

	rm-maxTrxs	OBJECT-TYPE
	    SYNTAX	INTEGER
	    MAX-ACCESS	read-write
	    STATUS	current
	    DESCRIPTION
		"Currently Unused"
	    DEFVAL
		{0}
	    ::= {resourceConfigData 8}

	rm-maxTchfs	OBJECT-TYPE
	    SYNTAX	INTEGER
	    MAX-ACCESS	read-write
	    STATUS	current
	    DESCRIPTION
		"Currently Unused"
	    DEFVAL
		{0}
	    ::= {resourceConfigData 9}

	rm-maxSdcch4s	OBJECT-TYPE
	    SYNTAX	INTEGER
	    MAX-ACCESS	read-write
	    STATUS	current
	    DESCRIPTION
		"Currently Unused"
	    DEFVAL
		{0}
	    ::= {resourceConfigData 10}

	rm-trxOnOffMap	OBJECT-TYPE
	    SYNTAX	INTEGER
	    MAX-ACCESS	read-write
	    STATUS	current
	    DESCRIPTION
		"Currently Unused"
	    DEFVAL
		{0}
	    ::= {resourceConfigData 11}

	rm-networkIfConfig	OBJECT-TYPE
	    SYNTAX	INTEGER
	    MAX-ACCESS	read-write
	    STATUS	current
	    DESCRIPTION
		"Currently Unused"
	    DEFVAL
		{0}
	    ::= {resourceConfigData 12}

	rm-bcchTrx	OBJECT-TYPE
	    SYNTAX	INTEGER
	    MAX-ACCESS	read-write
	    STATUS	current
	    DESCRIPTION
		"Currently Unused"
	    DEFVAL
		{0}
	    ::= {resourceConfigData 13}

	rm-preAlphaTrx	OBJECT-TYPE
	    SYNTAX	INTEGER
	    MAX-ACCESS	read-write
	    STATUS	current
	    DESCRIPTION
		"Currently Unused"
	    DEFVAL
		{0}
	    ::= {resourceConfigData 14}

	rm-ccchBcchComb	OBJECT-TYPE
	    SYNTAX	INTEGER
	    MAX-ACCESS	read-write
	    STATUS	current
	    DESCRIPTION
		"Currently Unused"
	    DEFVAL
		{0}
	    ::= {resourceConfigData 15}

	rm-ccchConf	OBJECT-TYPE
	    SYNTAX	INTEGER
	    MAX-ACCESS	read-write
	    STATUS	current
	    DESCRIPTION
		"Currently Unused"
	    DEFVAL
		{0}
	    ::= {resourceConfigData 16}
--
-- The following is actually a 2x8 array. That is 2 transmitters x 8 channels
-- In the C code, this is defined as "int rm_nim[2][8]" which has an identical
-- layout to the following:
--
	rm-nim-0-0	OBJECT-TYPE
	    SYNTAX	INTEGER
	    MAX-ACCESS	read-write
	    STATUS	current
	    DESCRIPTION
		"selection of physical beacon transceiver: normal or swap"
	    DEFVAL
		{0}
	    ::= {resourceConfigData 17}

	rm-nim-0-1	OBJECT-TYPE
	    SYNTAX	INTEGER
	    MAX-ACCESS	read-write
	    STATUS	current
	    DESCRIPTION
		"on-off control of cell broadcast short message feature"
	    DEFVAL
		{0}
	    ::= {resourceConfigData 18}

	rm-nim-0-2	OBJECT-TYPE
	    SYNTAX	INTEGER
	    MAX-ACCESS	read-write
	    STATUS	current
	    DESCRIPTION
		"on-off control of frequency hopping feature"
	    DEFVAL
		{0}
	    ::= {resourceConfigData 19}

	rm-nim-0-3	OBJECT-TYPE
	    SYNTAX	INTEGER
	    MAX-ACCESS	read-write
	    STATUS	current
	    DESCRIPTION
		"C2 parameter: cell reselection offset"
	    DEFVAL
		{0}
	    ::= {resourceConfigData 20}

	rm-nim-0-4	OBJECT-TYPE
	    SYNTAX	INTEGER
	    MAX-ACCESS	read-write
	    STATUS	current
	    DESCRIPTION
		"C2 parameter: temporary offset for cell reselection"
	    DEFVAL
		{0}
	    ::= {resourceConfigData 21}

	rm-nim-0-5	OBJECT-TYPE
	    SYNTAX	INTEGER
	    MAX-ACCESS	read-write
	    STATUS	current
	    DESCRIPTION
		"C2 parameter: penalty time for cell reselection"
	    DEFVAL
		{0}
	    ::= {resourceConfigData 22}

	rm-nim-0-6	OBJECT-TYPE
	    SYNTAX	INTEGER
	    MAX-ACCESS	read-write
	    STATUS	current
	    DESCRIPTION
		"cell bar qualify"
	    DEFVAL
		{0}
	    ::= {resourceConfigData 23}

	rm-nim-0-7	OBJECT-TYPE
	    SYNTAX	INTEGER
	    MAX-ACCESS	read-write
	    STATUS	current
	    DESCRIPTION
		"authentication frequency currently applied"
	    DEFVAL
		{0}
	    ::= {resourceConfigData 24}

	rm-nim-1-0	OBJECT-TYPE
	    SYNTAX	INTEGER
	    MAX-ACCESS	read-write
	    STATUS	current
	    DESCRIPTION
		"control if IMSI is required for an emergency call"
	    DEFVAL
		{0}
	    ::= {resourceConfigData 25}

	rm-nim-1-1	OBJECT-TYPE
	    SYNTAX	INTEGER
	    MAX-ACCESS	read-write
	    STATUS	current
	    DESCRIPTION
		"on-off control of overloaded cell barring feature"
	    DEFVAL
		{0}
	    ::= {resourceConfigData 26}

	rm-nim-1-2	OBJECT-TYPE
	    SYNTAX	INTEGER
	    MAX-ACCESS	read-write
	    STATUS	current
	    DESCRIPTION
		"Currently Unused"
	    DEFVAL
		{0}
	    ::= {resourceConfigData 27}

	rm-nim-1-3	OBJECT-TYPE
	    SYNTAX	INTEGER
	    MAX-ACCESS	read-write
	    STATUS	current
	    DESCRIPTION
		"Currently Unused"
	    DEFVAL
		{0}
	    ::= {resourceConfigData 28}

	rm-nim-1-4	OBJECT-TYPE
	    SYNTAX	INTEGER
	    MAX-ACCESS	read-write
	    STATUS	current
	    DESCRIPTION
		"Currently Unused"
	    DEFVAL
		{0}
	    ::= {resourceConfigData 29}

	rm-nim-1-5	OBJECT-TYPE
	    SYNTAX	INTEGER
	    MAX-ACCESS	read-write
	    STATUS	current
	    DESCRIPTION
		"Currently Unused"
	    DEFVAL
		{0}
	    ::= {resourceConfigData 30}

	rm-nim-1-6	OBJECT-TYPE
	    SYNTAX	INTEGER
	    MAX-ACCESS	read-write
	    STATUS	current
	    DESCRIPTION
		"Currently Unused"
	    DEFVAL
		{0}
	    ::= {resourceConfigData 31}

	rm-nim-1-7	OBJECT-TYPE
	    SYNTAX	INTEGER
	    MAX-ACCESS	read-write
	    STATUS	current
	    DESCRIPTION
		"Currently Unused"
	    DEFVAL
		{0}
	    ::= {resourceConfigData 32}

	rm-trxSynthSetting-0-0	OBJECT-TYPE
	    SYNTAX	INTEGER
	    MAX-ACCESS	read-write
	    STATUS	current
	    DESCRIPTION
		"Currently Unused"
	    DEFVAL
		{0}
	    ::= {resourceConfigData 33}

	rm-trxSynthSetting-0-1	OBJECT-TYPE
	    SYNTAX	INTEGER
	    MAX-ACCESS	read-write
	    STATUS	current
	    DESCRIPTION
		"Currently Unused"
	    DEFVAL
		{0}
	    ::= {resourceConfigData 34}

	rm-trxSynthSetting-0-2	OBJECT-TYPE
	    SYNTAX	INTEGER
	    MAX-ACCESS	read-write
	    STATUS	current
	    DESCRIPTION
		"Currently Unused"
	    DEFVAL
		{0}
	    ::= {resourceConfigData 35}

	rm-trxSynthSetting-0-3	OBJECT-TYPE
	    SYNTAX	INTEGER
	    MAX-ACCESS	read-write
	    STATUS	current
	    DESCRIPTION
		"Currently Unused"
	    DEFVAL
		{0}
	    ::= {resourceConfigData 36}

	rm-trxSynthSetting-1-0	OBJECT-TYPE
	    SYNTAX	INTEGER
	    MAX-ACCESS	read-write
	    STATUS	current
	    DESCRIPTION
		"Currently Unused"
	    DEFVAL
		{0}
	    ::= {resourceConfigData 37}

	rm-trxSynthSetting-1-1	OBJECT-TYPE
	    SYNTAX	INTEGER
	    MAX-ACCESS	read-write
	    STATUS	current
	    DESCRIPTION
		"Currently Unused"
	    DEFVAL
		{0}
	    ::= {resourceConfigData 38}

	rm-trxSynthSetting-1-2	OBJECT-TYPE
	    SYNTAX	INTEGER
	    MAX-ACCESS	read-write
	    STATUS	current
	    DESCRIPTION
		"Currently Unused"
	    DEFVAL
		{0}
	    ::= {resourceConfigData 39}

	rm-trxSynthSetting-1-3	OBJECT-TYPE
	    SYNTAX	INTEGER
	    MAX-ACCESS	read-write
	    STATUS	current
	    DESCRIPTION
		"Currently Unused"
	    DEFVAL
		{0}
	    ::= {resourceConfigData 40}

	rm-trxFpgaDelay-0-0	OBJECT-TYPE
	    SYNTAX	INTEGER
	    MAX-ACCESS	read-write
	    STATUS	current
	    DESCRIPTION
		"Currently Unused"
	    DEFVAL
		{0}
	    ::= {resourceConfigData 41}

	rm-trxFpgaDelay-0-1	OBJECT-TYPE
	    SYNTAX	INTEGER
	    MAX-ACCESS	read-write
	    STATUS	current
	    DESCRIPTION
		"Currently Unused"
	    DEFVAL
		{0}
	    ::= {resourceConfigData 42}

	rm-trxFpgaDelay-1-0	OBJECT-TYPE
	    SYNTAX	INTEGER
	    MAX-ACCESS	read-write
	    STATUS	current
	    DESCRIPTION
		"Currently Unused"
	    DEFVAL
		{0}
	    ::= {resourceConfigData 43}

	rm-trxFpgaDelay-1-1	OBJECT-TYPE
	    SYNTAX	INTEGER
	    MAX-ACCESS	read-write
	    STATUS	current
	    DESCRIPTION
		"Currently Unused"
	    DEFVAL
		{0}
	    ::= {resourceConfigData 44}

	rm-SGainCtrlSetting-0-0		OBJECT-TYPE
	    SYNTAX	INTEGER
	    MAX-ACCESS	read-write
	    STATUS	current
	    DESCRIPTION
		"Currently Unused"
	    DEFVAL
		{0}
	    ::= {resourceConfigData 45}

	rm-SGainCtrlSetting-0-1		OBJECT-TYPE
	    SYNTAX	INTEGER
	    MAX-ACCESS	read-write
	    STATUS	current
	    DESCRIPTION
		"Currently Unused"
	    DEFVAL
		{0}
	    ::= {resourceConfigData 46}

	rm-SGainCtrlSetting-1-0		OBJECT-TYPE
	    SYNTAX	INTEGER
	    MAX-ACCESS	read-write
	    STATUS	current
	    DESCRIPTION
		"Currently Unused"
	    DEFVAL
		{0}
	    ::= {resourceConfigData 47}

	rm-SGainCtrlSetting-1-1		OBJECT-TYPE
	    SYNTAX	INTEGER
	    MAX-ACCESS	read-write
	    STATUS	current
	    DESCRIPTION
		"Currently Unused"
	    DEFVAL
		{0}
	    ::= {resourceConfigData 48}

	rm-synchChanInfo	OBJECT-TYPE
	    SYNTAX	INTEGER
	    MAX-ACCESS	read-write
	    STATUS	current
	    DESCRIPTION
		"Currently Unused"
	    DEFVAL
		{0}
	    ::= {resourceConfigData 49}

oamConfigData OBJECT IDENTIFIER
-- 	DESCRIPTION
--		"OAM Configuration Data"
	::= {gp10ConfigMib 4}

	oamCommand	OBJECT-TYPE
	    SYNTAX	OamCommand
	    MAX-ACCESS	read-write
	    STATUS	current
	    DESCRIPTION
		"OAM command to be executed at the SNMP agent."
	    DEFVAL
		{0}
	    ::= {oamConfigData 1}

	oamCommandExecutionStatus	OBJECT-TYPE
	    SYNTAX	OamCommandExecutionStatus
	    MAX-ACCESS	read-write
	    STATUS	current
	    DESCRIPTION
		"Last OAM command execution status
		 inProgress (1), -- OAM Command is in progress. 
		 sucessful	 (2), -- Last OAM command was completed successfully
		 failed	 (3)  -- Last OAM command execution failed. Check oamCommandLastError to get text description of the error
		"
	    DEFVAL
		{0}
	    ::= {oamConfigData 2}

	oamAlternateMibFileName	OBJECT-TYPE
	    SYNTAX	DisplayString
	    MAX-ACCESS	read-write
	    STATUS	current
	    DESCRIPTION
		"An Alternate MIB file name which can be
		used to import and export MIB data. The default
		file name is always fixed as $(MNET_BASE)/mib/mib.txt"
	    ::= {oamConfigData 3}
	    	    
	oamCommandLastError	OBJECT-TYPE
	    SYNTAX	DisplayString
	    MAX-ACCESS	read-write
	    STATUS	current
	    DESCRIPTION
		"Text description of the last error occurred during the execution
		 of previous OAM command. This string is empty if there has not been
		 any error since the reboot of SNMP agent."
	    ::= {oamConfigData 4}

	mibAccessControlFlag	OBJECT-TYPE
		SYNTAX	Boolean
		MAX-ACCESS	read-write
		STATUS	current
		DESCRIPTION
		"Boolean flag to enable/disable access to MIB objects."
		::= {oamConfigData 5} 
				

maintenanceConfigData OBJECT IDENTIFIER
-- 	DESCRIPTION
--		"Maintenance Configuration Data"
	::= {gp10ConfigMib 5}

	maintenance-operation	OBJECT-TYPE
	    SYNTAX	DisplayString
	    MAX-ACCESS	read-write
	    STATUS	current
	    DESCRIPTION
		"Trigger a maintenance operation"
	    ::= {maintenanceConfigData 1}

	maintenance-response	OBJECT-TYPE
	    SYNTAX	DisplayString
	    MAX-ACCESS	read-write
	    STATUS	current
	    DESCRIPTION
		"Response to the last operation"
	    ::= {maintenanceConfigData 2}


gp10TrapConfigMib	OBJECT IDENTIFIER
--	DESCRIPTION
--		"Trap configuration information. The specifications of what to
--		 generate traps on and to whom they are sent to is defined as
--		 implementation specific. The handling of traps are different
--		 between the various versions of the SNMP protocol. Due to the
--		 lack of support for the full SNMPv2 standard by WindRiver, we
--		 generate a SNMPv1 TRAP PDU. The following information is used
--		 to generate these PDU's."
     --DEFAULT cookie MIBT_%n
	::= {gp10ConfigMib 6}

	trapFwdTable	OBJECT-TYPE
	    SYNTAX	SEQUENCE OF TrapFwdEntry
	    MAX-ACCESS	not-accessible
	    STATUS	current
	    DESCRIPTION
		"This entry is required to define a table of values."
	    ::= {gp10TrapConfigMib 1}

	trapFwdEntry	OBJECT-TYPE
	    SYNTAX	TrapFwdEntry
	    MAX-ACCESS	not-accessible
	    STATUS	current
	    DESCRIPTION
		"This attribute defines the set of trap config entries."
	    INDEX	{trapFwdIndex}
	    ::= {trapFwdTable 1}

	TrapFwdEntry	::= SEQUENCE {
	    trapFwdIndex		INTEGER,
   	    trapType			SnmpTrapType,       -- Type of trap SNMPv1 / SNMPv2.
	    trapIpAddress		IpAddress,		    -- IP address of the Manager interesting in this trap
	    trapPort			INTEGER,		    -- Manager's Trap Port.
	    trapCommunity		DisplayString		-- Community string to return to the manager.
	}

	trapFwdIndex	OBJECT-TYPE
	    SYNTAX	INTEGER (0..4)
	    MAX-ACCESS	read-only
	    STATUS	current
	    DESCRIPTION
		"Index to the trap Config table."
	    ::= {trapFwdEntry 1}

	trapType	OBJECT-TYPE
	    SYNTAX	SnmpTrapType
	    MAX-ACCESS	read-write
	    STATUS	current
	    DESCRIPTION
		"This specifies the type of Trap to be used (NONE / SNMPv1 / SNMPv2)"
	    ::= {trapFwdEntry 2}

	trapIpAddress	OBJECT-TYPE
	    SYNTAX	IpAddress
	    MAX-ACCESS	read-write
	    STATUS	current
	    DESCRIPTION
		"This contains the IpAddress of snmp mamager receiving trap"
	    ::= {trapFwdEntry 3}

	trapPort	OBJECT-TYPE
	    SYNTAX	INTEGER  (112..65535)
	    MAX-ACCESS	read-write
	    STATUS	current
	    DESCRIPTION
		"This specifies the trap port of the SNMP manager receiving trap."
	    ::= {trapFwdEntry 4}
	    
	trapCommunity	OBJECT-TYPE
	    SYNTAX	DisplayString
	    MAX-ACCESS	read-write
	    STATUS	current
	    DESCRIPTION
		"This is the community string to use in the Trap."
	    ::= {trapFwdEntry 5} 
	    
	sysTrapOid OBJECT-TYPE
		SYNTAX	OBJECT IDENTIFIER
	    MAX-ACCESS	not-accessible
	    STATUS	current
	    DESCRIPTION
		"The Object ID which identifies the notification type."
	    ::= {gp10TrapConfigMib 2}
	                       
	gp10TrapEvents  OBJECT IDENTIFIER ::= { gp10TrapConfigMib 3 }                       
	gp10TrapEventsV2 OBJECT IDENTIFIER ::= {gp10TrapEvents  0}                    
	
	trapCriticalAlarm  NOTIFICATION-TYPE
		OBJECTS {gp10ErrorInfoMib}
		STATUS current
		DESCRIPTION
		"Critical Alarm Trap."
        ::= {gp10TrapEventsV2 1} 
 	
 	trapMajorAlarm  NOTIFICATION-TYPE
		OBJECTS {gp10ErrorInfoMib}
		STATUS current
		DESCRIPTION
		"Major Alarm Trap."
        ::= {gp10TrapEventsV2 2} 
       
  	trapMinorAlarm  NOTIFICATION-TYPE
		OBJECTS {gp10ErrorInfoMib}
		STATUS current
		DESCRIPTION
		"Minor Alarm Trap."
        ::= {gp10TrapEventsV2 3} 

   	trapInformationAlarm  NOTIFICATION-TYPE
		OBJECTS {gp10ErrorInfoMib}
		STATUS current
		DESCRIPTION
		"Information Alarm Trap."
        ::= {gp10TrapEventsV2 4} 
   	

	trapAlarmModuleName OBJECT-TYPE
		SYNTAX	DisplayString
	    MAX-ACCESS	not-accessible
	    STATUS	current
	    DESCRIPTION
		"The alarm module name."
	    ::= {gp10TrapConfigMib 4}

	trapAlarmCode OBJECT-TYPE
		SYNTAX	INTEGER
	    MAX-ACCESS	not-accessible
	    STATUS	current
	    DESCRIPTION
		"The alarm code."
	    ::= {gp10TrapConfigMib 5}

	trapAlarmDesc OBJECT-TYPE
		SYNTAX	DisplayString
	    MAX-ACCESS	not-accessible
	    STATUS	current
	    DESCRIPTION
		"The alarm description."
	    ::= {gp10TrapConfigMib 6}

--
--	ViperCell Configuration Information
--

dualTRXSCard OBJECT IDENTIFIER
-- 	DESCRIPTION
--		"Dual TRX Status"
	::= {gp10SpecificMib 1}

	monitorReceiverPLL-LockDetectStatus	OBJECT-TYPE
	    SYNTAX	INTEGER
	    MAX-ACCESS	read-write
	    STATUS	current
	    DESCRIPTION
		"Lock Detect Status of the Monitor Receiver's PLL"
	    DEFVAL
		{0}
	    ::= {dualTRXSCard 1}

	referenceFrequencyPLL-LockDetectStatus	OBJECT-TYPE
	    SYNTAX	INTEGER
	    MAX-ACCESS	read-write
	    STATUS	current
	    DESCRIPTION
		"Lock Detect Status of the Reference Frequency's PLL"
	    DEFVAL
		{0}
	    ::= {dualTRXSCard 2}

	transceiver-1-PLL-LockDetectStatus	OBJECT-TYPE
	    SYNTAX	INTEGER
	    MAX-ACCESS	read-write
	    STATUS	current
	    DESCRIPTION
		"Lock Detect Status of the Transceiver #1 PLL"
	    DEFVAL
		{0}
	    ::= {dualTRXSCard 3}

	transceiver-2A-PLL-LockDetectStatus	OBJECT-TYPE
	    SYNTAX	INTEGER
	    MAX-ACCESS	read-write
	    STATUS	current
	    DESCRIPTION
		"Lock Detect Status of the Transceiver #2A PLL"
	    DEFVAL
		{0}
	    ::= {dualTRXSCard 4}

	transceiver-2B-PLL-LockDetectStatus	OBJECT-TYPE
	    SYNTAX	INTEGER
	    MAX-ACCESS	read-write
	    STATUS	current
	    DESCRIPTION
		"Lock Detect Status of the Transceiver #2B PLL"
	    DEFVAL
		{0}
	    ::= {dualTRXSCard 5}

	intermediateFrequency-LockDetectStatus	OBJECT-TYPE
	    SYNTAX	INTEGER
	    MAX-ACCESS	read-write
	    STATUS	current
	    DESCRIPTION
		"Lock Detect Status of the Intermediate Frequency's PLL"
	    DEFVAL
		{0}
	    ::= {dualTRXSCard 6}

	trxSerialNumber	OBJECT-TYPE
	    SYNTAX	DisplayString
	    MAX-ACCESS	read-only
	    STATUS	current
	    DESCRIPTION
		"Hardware Serial Number of the TRX Card"
	    ::= {dualTRXSCard 7}

	trxSoftwareVersion	OBJECT-TYPE
	    SYNTAX	DisplayString
	    MAX-ACCESS	read-only
	    STATUS	current
	    DESCRIPTION
		"Software Version Number of the TRX Card"
	    ::= {dualTRXSCard 8}

	trxLoopBackMode	OBJECT-TYPE
	    SYNTAX	LoopBackControlCode
	    MAX-ACCESS	read-write
	    STATUS	current
	    DESCRIPTION
		"Loop Back Mode"
	    DEFVAL
		{0}
	    ::= {dualTRXSCard 9}

arfcnRssiFunction OBJECT IDENTIFIER
-- 	DESCRIPTION
--		"ARFCN RSSI function"
	::= {gp10SpecificMib 2}

	arfcnRssiControlMode	OBJECT-TYPE
	    SYNTAX		EnableDisable
	    MAX-ACCESS		read-write
	    STATUS		current
	    DESCRIPTION
		"ARFCN/RSSI Function Control"
	    DEFVAL
		{0}
	    ::= {arfcnRssiFunction 1}

	clockRecoveryControlMode	OBJECT-TYPE
	    SYNTAX		RecoveryMode
	    MAX-ACCESS		read-write
	    STATUS		current
	    DESCRIPTION
		"Clock Recovery Feature Control"
	    DEFVAL
		{0}
	    ::= {arfcnRssiFunction 2}

	arfcnRssiClockControlTable	OBJECT-TYPE
	    SYNTAX	SEQUENCE OF ArfcnRssiClockControlEntry
	    MAX-ACCESS	not-accessible
	    STATUS	current
	    DESCRIPTION
		"This entry is required to define a table of values."
	    ::= {arfcnRssiFunction 3}

	arfcnRssiClockControlEntry	OBJECT-TYPE
	    SYNTAX	ArfcnRssiClockControlEntry
	    MAX-ACCESS	not-accessible
	    STATUS	current
	    DESCRIPTION
		"This attribute defines the set of ."
	    INDEX	{arfcnRssiClockControlIndex}
	    --DEFAULT cookie MIBT_%n
	    ::= {arfcnRssiClockControlTable 1}

	ArfcnRssiClockControlEntry	::= SEQUENCE {
	    arfcnRssiClockControlIndex		INTEGER,
	    arfcnRssiClockControlArfcn		AbsoluteRFChannelNo,
	    arfcnRssiClockRecoveryMode		EnableDisable
	}

	arfcnRssiClockControlIndex	OBJECT-TYPE
	    SYNTAX	INTEGER -- (0..63)
	    MAX-ACCESS	read-only
	    STATUS	current
	    DESCRIPTION
		"Index to the ARFCN/RSSI/ClockControl table."
	    ::= {arfcnRssiClockControlEntry 1}

	arfcnRssiClockControlArfcn	OBJECT-TYPE
	    SYNTAX	AbsoluteRFChannelNo
	    MAX-ACCESS	read-write
	    STATUS	current
	    DESCRIPTION
		"RF Channel No"
	    ::= {arfcnRssiClockControlEntry 2}

	arfcnRssiClockRecoveryMode	OBJECT-TYPE
	    SYNTAX	EnableDisable
	    MAX-ACCESS	read-write
	    STATUS	current
	    DESCRIPTION
		"Clock Syncronization"
	    ::= {arfcnRssiClockControlEntry 3}

clockCard OBJECT IDENTIFIER
-- 	DESCRIPTION
--		"Clock Card"
	::= {gp10SpecificMib 3}

	clockCardType	OBJECT-TYPE
	    SYNTAX	INTEGER
	    MAX-ACCESS	read-only
	    STATUS	current
	    DESCRIPTION
		"Clock Card types"
	    DEFVAL
		{0}
	    ::= {clockCard 1}

	clockCardSoftwareVersion	OBJECT-TYPE
	    SYNTAX	DisplayString
	    MAX-ACCESS	read-only
	    STATUS	current
	    DESCRIPTION
		"Software Version of the Clock Card"
	    ::= {clockCard 2}

	clockCardStatus	OBJECT-TYPE
	    SYNTAX	INTEGER
	    MAX-ACCESS	read-only
	    STATUS	current
	    DESCRIPTION
		"Clock Card Status - validity of clock output"
	    DEFVAL
		{0}
	    ::= {clockCard 3}

	clockCardCrystalUpTime	OBJECT-TYPE
	    SYNTAX	DisplayString
	    MAX-ACCESS	read-only
	    STATUS	current
	    DESCRIPTION
		"Crystal Up-time of the Clock Card"
	    ::= {clockCard 4}

	clockCardDAC	OBJECT-TYPE
	    SYNTAX	INTEGER
	    MAX-ACCESS	read-write
	    STATUS	current
	    DESCRIPTION
		"Clock Card DAC value"
	    DEFVAL
		{0}
	    ::= {clockCard 5}

gpsCard OBJECT IDENTIFIER
-- 	DESCRIPTION
--		"GPS Card"
	::= {gp10SpecificMib 4}

	gpsCardType	OBJECT-TYPE
	    SYNTAX	INTEGER
	    MAX-ACCESS	read-only
	    STATUS	current
	    DESCRIPTION
		"GPS Card types"
	    DEFVAL
		{0}
	    ::= {gpsCard 1}

	gpsCardSoftwareVersion	OBJECT-TYPE
	    SYNTAX	DisplayString
	    MAX-ACCESS	read-only
	    STATUS	current
	    DESCRIPTION
		"Software Version of the GPS Card"
	    ::= {gpsCard 2}

	gpsCardStatus	OBJECT-TYPE
	    SYNTAX	INTEGER
	    MAX-ACCESS	read-only
	    STATUS	current
	    DESCRIPTION
		"GPS Card General Status"
	    DEFVAL
		{0}
	    ::= {gpsCard 3}

	gpsPosition	OBJECT-TYPE
	    SYNTAX	DisplayString
	    MAX-ACCESS	read-write
	    STATUS	current
	    DESCRIPTION
		"Longitude and Latitude"
	    ::= {gpsCard 4}

	gpsTime	OBJECT-TYPE
	    SYNTAX	DisplayString
	    MAX-ACCESS	read-only
	    STATUS	current
	    DESCRIPTION
		"GPS Time"
	    ::= {gpsCard 5}

	utcTime	OBJECT-TYPE
	    SYNTAX	DisplayString
	    MAX-ACCESS	read-only
	    STATUS	current
	    DESCRIPTION
		"UTC Time"
	    ::= {gpsCard 6}

	clockStatusFrequencyError	OBJECT-TYPE
	    SYNTAX	INTEGER
	    MAX-ACCESS	read-only
	    STATUS	current
	    DESCRIPTION
		"Clock Status - Frequency Error"
	    ::= {gpsCard 7}

	clockStatusDACVoltage	OBJECT-TYPE
	    SYNTAX	INTEGER
	    MAX-ACCESS	read-only
	    STATUS	current
	    DESCRIPTION
		"Clock Status - DAC Voltage"
	    ::= {gpsCard 8}

	gpsAntennaStatus	OBJECT-TYPE
	    SYNTAX	INTEGER
	    MAX-ACCESS	read-only
	    STATUS	current
	    DESCRIPTION
		"Antenna Status"
	    ::= {gpsCard 9}

	gpsSatelliteStatus	OBJECT-TYPE
	    SYNTAX	INTEGER
	    MAX-ACCESS	read-only
	    STATUS	current
	    DESCRIPTION
		"Satellite Status"
	    ::= {gpsCard 10}

powerCard OBJECT IDENTIFIER
-- 	DESCRIPTION
--		"Power Card"
	::= {gp10SpecificMib 5}

	powerCardType	OBJECT-TYPE
	    SYNTAX	INTEGER
	    MAX-ACCESS	read-only
	    STATUS	current
	    DESCRIPTION
		"powerCard  types"
	    DEFVAL
		{0}
	    ::= {powerCard 1}

	powerCardStatus	OBJECT-TYPE
	    SYNTAX	INTEGER
	    MAX-ACCESS	read-only
	    STATUS	current
	    DESCRIPTION
		"Power Card General Status"
	    DEFVAL
		{0}
	    ::= {powerCard 2}

	powerOn	OBJECT-TYPE
	    SYNTAX	PowerStatus
	    MAX-ACCESS	read-write
	    STATUS	current
	    DESCRIPTION
		"Switch of the power Card (none-reversible action when turn-off)"
	    DEFVAL
		{1}
    	    ::= {powerCard 3}

externalPowerSupply OBJECT IDENTIFIER
-- 	DESCRIPTION
--		"External Power Supply"
	::= {gp10SpecificMib 6}

	powerSupplyType	OBJECT-TYPE
	    SYNTAX	PowerSupplyType
	    MAX-ACCESS	read-only
	    STATUS	current
	    DESCRIPTION
		"External Power Supply type"
	    DEFVAL
		{0}
	    ::= {externalPowerSupply 1}

	powerSupplyStatus	OBJECT-TYPE
	    SYNTAX	INTEGER
	    MAX-ACCESS	read-only
	    STATUS	current
	    DESCRIPTION
		"Power Supply General Status"
	    DEFVAL
		{0}
	    ::= {externalPowerSupply 2}


cdcBoard OBJECT IDENTIFIER
-- 	DESCRIPTION
--		"CDC Board"
	::= {gp10SpecificMib 7}

	cdcBoardSerialNumber	OBJECT-TYPE
	    SYNTAX	DisplayString
	    MAX-ACCESS	read-only
	    STATUS	current
	    DESCRIPTION
		"cdcBoard Serial Number"
	    ::= {cdcBoard 1}

	cdcBoardMACAddress	OBJECT-TYPE
	    SYNTAX	DisplayString
	    MAX-ACCESS	read-only
	    STATUS	current
	    DESCRIPTION
		"CDC board MAC Address"
	    ::= {cdcBoard 2}

automaticParameterAllocation OBJECT IDENTIFIER
-- 	DESCRIPTION
--		"CDC Board"
	::= {gp10SpecificMib 8}

	apaEnable 	OBJECT-TYPE
	    SYNTAX	INTEGER { disable(0), enabled(1) }
	    MAX-ACCESS	read-write
	    STATUS	current
	    DESCRIPTION
		"Feature Enable"
	    DEFVAL
		{0}
	    ::= {automaticParameterAllocation 1}

	apaScanFrequencyLowBound 	OBJECT-TYPE
	    SYNTAX	INTEGER
	    MAX-ACCESS	read-write
	    STATUS	current
	    DESCRIPTION
		"Low bound of the Feaquencies to be scaned"
	    DEFVAL
		{0}
	    ::= {automaticParameterAllocation 2}

	apaScanFrequencyHighBound 	OBJECT-TYPE
	    SYNTAX	INTEGER
	    MAX-ACCESS	read-write
	    STATUS	current
	    DESCRIPTION
		"High bound of the Feaquencies to be scaned"
	    DEFVAL
		{0}
	    ::= {automaticParameterAllocation 3}

	apaMaxPowerSetting	OBJECT-TYPE
	    SYNTAX	INTEGER
	    MAX-ACCESS	read-write
	    STATUS	current
	    DESCRIPTION
		"Max power setting for ViperCell"
	    DEFVAL
		{0}
	    ::= {automaticParameterAllocation 4}

	apaMinRSSIThresholdForNeighborId	OBJECT-TYPE
	    SYNTAX	INTEGER
	    MAX-ACCESS	read-write
	    STATUS	current
	    DESCRIPTION
		"Minimum RSSI value below which the unit is not a neighbor"
	    DEFVAL
		{0}
	    ::= {automaticParameterAllocation 5}

	apaScanRate	OBJECT-TYPE
	    SYNTAX	INTEGER
	    MAX-ACCESS	read-write
	    STATUS	current
	    DESCRIPTION
		"Scan Rate for checking RSSI value (in unit of TBD)"
	    DEFVAL
		{0}
	    ::= {automaticParameterAllocation 6}

	apaHysteresisForBCCHPower	OBJECT-TYPE
	    SYNTAX	INTEGER
	    MAX-ACCESS	read-write
	    STATUS	current
	    DESCRIPTION
		"Hysteresis for change the power on the BCCH"
	    DEFVAL
		{0}
	    ::= {automaticParameterAllocation 7}
    
	apaInvalidFrequencyTable	OBJECT-TYPE
	    SYNTAX	SEQUENCE OF ApaInvalidFrequencyEntry
	    MAX-ACCESS	not-accessible
	    STATUS	current
	    DESCRIPTION
		"This entry is required to define a table of values."
	    ::= {automaticParameterAllocation 8} 
 
  	apaInvalidFrequencyEntry	OBJECT-TYPE
	    SYNTAX	ApaInvalidFrequencyEntry
	    MAX-ACCESS	not-accessible
	    STATUS	current
	    DESCRIPTION
		"This attribute defines the set of invalid frequencies within the scan frequency range."
	    INDEX	{apaInvalidFrequencyIndex}
	    --DEFAULT cookie MIBT_%n
	    ::= {apaInvalidFrequencyTable 1}

	ApaInvalidFrequencyEntry	::= SEQUENCE {
	    apaInvalidFrequencyIndex		INTEGER,
	    apaInvalidFrequencyArfcn		AbsoluteRFChannelNo
	}

	apaInvalidFrequencyIndex	OBJECT-TYPE
	    SYNTAX	INTEGER -- (0..63)
	    MAX-ACCESS	read-only
	    STATUS	current
	    DESCRIPTION
		"Index to the apa Invalid Frequency table."
	    ::= {apaInvalidFrequencyEntry 1}   


	apaInvalidFrequencyArfcn	OBJECT-TYPE
	    SYNTAX	AbsoluteRFChannelNo
	    MAX-ACCESS	read-write
	    STATUS	current
	    DESCRIPTION
		"Index to the apa Invalid Frequency table."
	    ::= {apaInvalidFrequencyEntry 2}   
	
	apaClockSourceFrequencyTable	OBJECT-TYPE
	    SYNTAX	SEQUENCE OF ApaClockSourceFrequencyEntry
	    MAX-ACCESS	not-accessible
	    STATUS	current
	    DESCRIPTION
		"This entry is required to define a table of values."
	    ::= {automaticParameterAllocation 9}  
	    
 	apaClockSourceFrequencyEntry	OBJECT-TYPE
	    SYNTAX	ApaClockSourceFrequencyEntry
	    MAX-ACCESS	not-accessible
	    STATUS	current
	    DESCRIPTION
		"This attribute defines the set of clock source frequencies."
	    INDEX	{apaClockSourceFrequencyIndex}
	    --DEFAULT cookie MIBT_%n
	    ::= {apaClockSourceFrequencyTable 1}

 	ApaClockSourceFrequencyEntry	::= SEQUENCE {
	    apaClockSourceFrequencyIndex	INTEGER,
	    apaClockSourceFrequencyArfcn	AbsoluteRFChannelNo
	}

	apaClockSourceFrequencyIndex	OBJECT-TYPE
	    SYNTAX	INTEGER -- (0..63)
	    MAX-ACCESS	read-only
	    STATUS	current
	    DESCRIPTION
		"Index to the apa Invalid Frequency table."
	    ::= {apaClockSourceFrequencyEntry 1}

	apaClockSourceFrequencyArfcn	OBJECT-TYPE
	    SYNTAX	AbsoluteRFChannelNo
	    MAX-ACCESS	read-write
	    STATUS	current
	    DESCRIPTION
		"Apa Invalid Frequency."
	    ::= {apaClockSourceFrequencyEntry 2}

-- gp10MgmtInfoMib OBJECT IDENTIFIER
-- 	DESCRIPTION
--		"ViperCell General Management Information.
--		 In general, these values are not used in
--		 the actual operations of the ViperCell but
--		 they are useful bits of information to be
--		 stored for use by Management applications."
--	::= {gp10Mib 5}

    viperCellName	OBJECT-TYPE
	    SYNTAX	DisplayString
	    MAX-ACCESS	read-write
	    STATUS	current
	    DESCRIPTION
		"The name of the ViperCell"
	    ::= {gp10MgmtInfoMib 1}

	viperCellIPAddress	OBJECT-TYPE
	    SYNTAX	IpAddress
	    MAX-ACCESS	read-write
	    STATUS	current
	    DESCRIPTION
		"IP Address of the ViperCell"
	    ::= {gp10MgmtInfoMib 2}
	
	viperCellDefGateway		OBJECT-TYPE
	    SYNTAX	IpAddress
	    MAX-ACCESS	read-write
	    STATUS	current
	    DESCRIPTION
		"Default gateway of this network element."
	    ::= {gp10MgmtInfoMib 3}	    

	viperCellLocation	OBJECT-TYPE
	    SYNTAX	DisplayString
	    MAX-ACCESS	read-write
	    STATUS	current
	    DESCRIPTION
		"Location of the ViperCell"
	    ::= {gp10MgmtInfoMib 4}

	viperCellSerialNumber	OBJECT-TYPE
	    SYNTAX	DisplayString
	    MAX-ACCESS	read-write
	    STATUS	current
	    DESCRIPTION
		"Serial Number of the ViperCell"
	    ::= {gp10MgmtInfoMib 5}

	viperCellAssetNumber	OBJECT-TYPE
	    SYNTAX	DisplayString
	    MAX-ACCESS	read-write
	    STATUS	current
	    DESCRIPTION
		"Asset Number or other Customer tracking information"
	    ::= {gp10MgmtInfoMib 6}

	viperCellSoftwareBuild	OBJECT-TYPE
	    SYNTAX	DisplayString
	    MAX-ACCESS	read-only
	    STATUS	current
	    DESCRIPTION
		"Date upon which the ViperCell software was created"
	    ::= {gp10MgmtInfoMib 7}

	viperCellCustomerName	OBJECT-TYPE
	    SYNTAX	DisplayString
	    MAX-ACCESS	read-write
	    STATUS	current
	    DESCRIPTION
		"Name of the Customer who owns the ViperCell"
	    ::= {gp10MgmtInfoMib 8}

	viperCellCustomerAddress	OBJECT-TYPE
	    SYNTAX	DisplayString
	    MAX-ACCESS	read-write
	    STATUS	current
	    DESCRIPTION
		"Address of who Customer who owns the ViperCell"
	    ::= {gp10MgmtInfoMib 9}

	viperCellCustomerPhone	OBJECT-TYPE
	    SYNTAX	DisplayString
	    MAX-ACCESS	read-write
	    STATUS	current
	    DESCRIPTION
		"Phone Number of who Customer who owns the ViperCell"
	    ::= {gp10MgmtInfoMib 10}

	viperCellCustomerEmail	OBJECT-TYPE
	    SYNTAX	DisplayString
	    MAX-ACCESS	read-write
	    STATUS	current
	    DESCRIPTION
		"Email of who to Customer who owns the ViperCell"
	    ::= {gp10MgmtInfoMib 11}


	viperCellCustomerInfo	OBJECT-TYPE
	    SYNTAX	DisplayString
	    MAX-ACCESS	read-write
	    STATUS	current
	    DESCRIPTION
		"For any general information the customer wishes to store"
	    ::= {gp10MgmtInfoMib 12}


-- gp10ErrorInfoMib OBJECT IDENTIFIER
-- 	DESCRIPTION
--		"ViperCell General Management Information.
--		 In general, these values are not used in
--		 the actual operations of the ViperCell but
--		 they are useful bits of information to be
--		 stored for use by Management applications."
--	::= {gp10Mib 6}

	errorCode-L1	OBJECT-TYPE
	    SYNTAX	INTEGER
	    MAX-ACCESS	read-only
	    STATUS	current
	    DESCRIPTION
		"Alarm Error Code for DSP Interface Driver Module"
	    ::= {gp10ErrorInfoMib 1}

	errorCode-MD	OBJECT-TYPE
	    SYNTAX	INTEGER
	    MAX-ACCESS	read-only
	    STATUS	current
	    DESCRIPTION
		"Alarm Error Code for RIL3 Message Delivery"
	    ::= {gp10ErrorInfoMib 2}

	errorCode-RM	OBJECT-TYPE
	    SYNTAX	INTEGER
	    MAX-ACCESS	read-only
	    STATUS	current
	    DESCRIPTION
		"Alarm Error Code for RR functional entity"
	    ::= {gp10ErrorInfoMib 3}

	errorCode-MM	OBJECT-TYPE
	    SYNTAX	INTEGER
	    MAX-ACCESS	read-only
	    STATUS	current
	    DESCRIPTION
		"Alarm Error Code for MM functional entity"
	    ::= {gp10ErrorInfoMib 4}

	errorCode-CC	OBJECT-TYPE
	    SYNTAX	INTEGER
	    MAX-ACCESS	read-only
	    STATUS	current
	    DESCRIPTION
		"Alarm Error Code for CC functional entity"
	    ::= {gp10ErrorInfoMib 5}

	errorCode-L2	OBJECT-TYPE
	    SYNTAX	INTEGER
	    MAX-ACCESS	read-only
	    STATUS	current
	    DESCRIPTION
		"Alarm Error Code for LAPDm functional entity"
	    ::= {gp10ErrorInfoMib 6}

	errorCode-SMS	OBJECT-TYPE
	    SYNTAX	INTEGER
	    MAX-ACCESS	read-only
	    STATUS	current
	    DESCRIPTION
		"Alarm Error Code for SMS functional entity"
	    ::= {gp10ErrorInfoMib 7}

	errorCode-OAM	OBJECT-TYPE
	    SYNTAX	INTEGER
	    MAX-ACCESS	read-only
	    STATUS	current
	    DESCRIPTION
		"Alarm Error Code for OAM functional entity"
	    ::= {gp10ErrorInfoMib 8}

	errorCode-H323	OBJECT-TYPE
	    SYNTAX	INTEGER
	    MAX-ACCESS	read-only
	    STATUS	current
	    DESCRIPTION
		"Alarm Error Code for H323 Stack and Application Layers"
	    ::= {gp10ErrorInfoMib 9}

	errorCode-LUDB	OBJECT-TYPE
	    SYNTAX	INTEGER
	    MAX-ACCESS	read-only
	    STATUS	current
	    DESCRIPTION
		"Alarm Error Code for Local User Database Module"
	    ::= {gp10ErrorInfoMib 10}

	errorCode-EXT-LC	OBJECT-TYPE
	    SYNTAX	INTEGER
	    MAX-ACCESS	read-only
	    STATUS	current
	    DESCRIPTION
		"Alarm Error Code for Generated by external GP10"
	    ::= {gp10ErrorInfoMib 11}

	errorCode-LOG	OBJECT-TYPE
	    SYNTAX	INTEGER
	    MAX-ACCESS	read-only
	    STATUS	current
	    DESCRIPTION
		"Alarm Error Code for System Logger"
	    ::= {gp10ErrorInfoMib 12}

	errorCode-MCH	OBJECT-TYPE
	    SYNTAX	INTEGER
	    MAX-ACCESS	read-only
	    STATUS	current
	    DESCRIPTION
		"Alarm Error Code for Maintenance Command Handler Module"
	    ::= {gp10ErrorInfoMib 13}

	errorCode-ALARM	OBJECT-TYPE
	    SYNTAX	INTEGER
	    MAX-ACCESS	read-only
	    STATUS	current
	    DESCRIPTION
		"Alarm Error Code for Local Alarm Module"
	    ::= {gp10ErrorInfoMib 14}

	errorCode-SYSINIT	OBJECT-TYPE
	    SYNTAX	INTEGER
	    MAX-ACCESS	read-only
	    STATUS	current
	    DESCRIPTION
		"Alarm Error Code for System Initialization Module"
	    ::= {gp10ErrorInfoMib 15}

	errorCode-GRR	OBJECT-TYPE
	    SYNTAX	INTEGER
	    MAX-ACCESS	read-only
	    STATUS	current
	    DESCRIPTION
		"Alarm Error Code for GRR Module"
	    ::= {gp10ErrorInfoMib 16}

	errorCode-CDR	OBJECT-TYPE
	    SYNTAX	INTEGER
	    MAX-ACCESS	read-only
	    STATUS	current
	    DESCRIPTION
		"Alarm Error Code for CDR Module"
	    ::= {gp10ErrorInfoMib 17}

-- GP10 Enhancements to support GPRS Server (GS)
--
--	Gp10Gprs MIB
--
--	The Gp10 MIB is organized into 7 sub-leafs. This MIB file is a consolidation 
--	of information based on configuration and measurement parameters
--  required for supporting GPRS Server (GS)

--	The gp10gprsMib is broken into several leafs as follows: 
--
--	1:	btsGsBasicPackage			Basic Parameters (primarily RM) 
--  2:  btsGsInterfacePackage		Interface parameters with GS.
--	3:	btsGsMeasPackage		Performance measurment data
--

btsGsBasicPackage OBJECT IDENTIFIER
-- 	DESCRIPTION
-- 		"The GP10 needs to be aware of the GS, for sending Location Update 
--		 Request and other data communication. For this it has to be aware of
--		 GS IP Address and Routing Area Code (RAC). Both this are configuration
--		 parameters that can be set by the user."
	::= {gp10GprsMib 1}

	gprsServerIpAddress		OBJECT-TYPE
	    SYNTAX	IpAddress
	    MAX-ACCESS	read-write
	    STATUS	current
	    DESCRIPTION
		"This attribute contains the GPRS Servers (GS) IP Address."
	    ::= {btsGsBasicPackage 1}

	gprsRac	OBJECT-TYPE
	    SYNTAX	INTEGER
	    MAX-ACCESS	read-write
	    STATUS	current
	    DESCRIPTION
		"Routing Area Code to indicate which RA this Gp10 belongs to."
	    ::= {btsGsBasicPackage 2}   

	enableGprs	OBJECT-TYPE
		SYNTAX EnableDisable
		MAX-ACCESS read-write
		STATUS current
		DESCRIPTION
		"This attribute will be used by the operator to enable or diable
		 GPRS feature."
		 ::= {btsGsBasicPackage 3}	    

	gprsOperationalStatus	OBJECT-TYPE
		SYNTAX OperationalState
		MAX-ACCESS read-only
		STATUS current
		DESCRIPTION
		"This attribute will be used by the operator to check the
		operation status of GPRS Server."
  		 ::= {btsGsBasicPackage 4}
	
btsGsOptionPackage	OBJECT IDENTIFIER
-- 	DESCRIPTION
-- 		"The GP10 cell option parameters to support gprs."
	::= {gp10GprsMib 2}         
	
	nmo OBJECT-TYPE
		SYNTAX	INTEGER (0..3)
	    MAX-ACCESS	read-write
	    STATUS	current
	    DESCRIPTION
		"The maximum TX power level an MS may use 
		when accessing the system."  
		DEFVAL {1}
	    ::= {btsGsOptionPackage 1}	
	    
	t3168 OBJECT-TYPE
		SYNTAX	INTEGER (0..7)
	    MAX-ACCESS	read-write
	    STATUS	current
	    DESCRIPTION
		"TimeOut value for t3168, The timeout value is given as 
		the value plus one, in units of 500 msecs."
		DEFVAL {4}
	    ::= {btsGsOptionPackage 2}

	t3192 OBJECT-TYPE
		SYNTAX	INTEGER (0..7)
	    MAX-ACCESS	read-write
	    STATUS	current
	    DESCRIPTION
		"TimeOut value for t3192, The timeout values are
		500, 1000, 1500, 0, 80, 120, 160, 200. In case of 0 msec
		the timer is not started."
		DEFVAL {3}
	    ::= {btsGsOptionPackage 3}

	drxTimerMax OBJECT-TYPE
		SYNTAX	INTEGER (0..7)
	    MAX-ACCESS	read-write
	    STATUS	current
	    DESCRIPTION
		"The field is a binary representation of the parameter DRX_TIMER_MAX.
		The parameter value is given as two taken to the power of the binary value
		minus one (2^n - 1).
		i.e. 0,1,2,4,8,16,32,64 secs"
		DEFVAL {7}
	    ::= {btsGsOptionPackage 4}

	accessBurstType OBJECT-TYPE
		SYNTAX	INTEGER (0..1)
	    MAX-ACCESS	read-write
	    STATUS	current
	    DESCRIPTION
		"Indicates if 8 or 11 bit access burst shall be used on
		PRACH, PTCCH/U and in the PACKET CONTROL ACKNOWLEDGEMENT
		message when the format is four access bursts.
		0 - 8 bit access burst shall be used
		1 - 11 bit access burst shall be used."
		DEFVAL {0}
	    ::= {btsGsOptionPackage 5}
	    
	    
	controlAckType OBJECT-TYPE
		SYNTAX	INTEGER (0..1)
	    MAX-ACCESS	read-write
	    STATUS	current
	    DESCRIPTION
		"Represents the default format of the PACKET CONTROL
		ACKNOWLEDGEMENT message.
		0 - format is four access bursts
		1 - format is RLC/MAC control block."                           
		DEFVAL {0}
	    ::= {btsGsOptionPackage 6}	    	    	    	    	    
	    
	bsCvMax OBJECT-TYPE
		SYNTAX	INTEGER (0..15)
	    MAX-ACCESS	read-write
	    STATUS	current
	    DESCRIPTION
		"Represents the parameter BS_CV_MAX.
		The value BS_CV_MAX = 0 shall be interpreted as
		value BS_CV_MAX=1 for claculation of T3198, T3200 and
		N3104max Values." 
		DEFVAL {7}
	    ::= {btsGsOptionPackage 7}	    	    	    	    	    
	    
	panDec OBJECT-TYPE
		SYNTAX	INTEGER (0..7)
	    MAX-ACCESS	read-write
	    STATUS	current
	    DESCRIPTION
		"Represents the parameter PAN_DEC."
		DEFVAL {1}
	    ::= {btsGsOptionPackage 8}	    	    	    	    	    
	    
	panInc OBJECT-TYPE
		SYNTAX	INTEGER (0..7)
	    MAX-ACCESS	read-write
	    STATUS	current
	    DESCRIPTION
		"Represents the parameter PAN_INC."
		DEFVAL {1}
	    ::= {btsGsOptionPackage 9}	    	    	    	    	    
	    
	panMax OBJECT-TYPE
		SYNTAX	INTEGER (0..7)
	    MAX-ACCESS	read-write
	    STATUS	current
	    DESCRIPTION
		"Represents the maximum value allowed for counter
		N3102.
		0 - 4
		1 - 8
		2 - 12
		3 - 16
		4 - 20
		5 - 24
		6 - 28
		7 - 32."
		DEFVAL {4}
	    ::= {btsGsOptionPackage 10}	    	    	    	    	    
		 
	raColour OBJECT-TYPE
		SYNTAX      NetworkColourCode		-- INTEGER (0..7)
		MAX-ACCESS  read-write
		STATUS      current
		DESCRIPTION
		"If the mobile station receives different
		values of the RA COLOUR field in different cell,
		the mobile station shall interpret the cell re-selection
		information as if the two cells belong to different routing areas.."
		DEFVAL {0}
		::= {btsGsOptionPackage 11}

	si13Position OBJECT-TYPE
		SYNTAX      Si13Position			-- INTEGER (0..1)
		MAX-ACCESS  read-write
		STATUS      current
		DESCRIPTION
		"The SI13 POSITION indicates the minimum schedule for
		where the SYSTEM INFORMATION TYPE 13 message is sent on BCCH."
		DEFVAL {0}
		::= {btsGsOptionPackage 12}

	cbchTrxSlot OBJECT-TYPE
		SYNTAX      CbchTrxSlot				-- INTEGER (0..7)
		MAX-ACCESS  read-write
		STATUS      current
		DESCRIPTION
		"This value indicates the Timeslot Number for TN field of
		SI4 message."
		DEFVAL {0}
		::= {btsGsOptionPackage 13}

	cbchTrx OBJECT-TYPE
		SYNTAX      CbchTrx					-- INTEGER (0..1)
		MAX-ACCESS  read-write
		STATUS      current
		DESCRIPTION
		"This value  means the logical number for carrier frequency.
		The ARFCN field of SI4 message is coded as binary
		representation of the absolute RF channel number by this value."
		DEFVAL {0}
		::= {btsGsOptionPackage 14}

	bcchChangeMark OBJECT-TYPE
		SYNTAX      BcchChangeMark			-- INTEGER (0..3)
		MAX-ACCESS  read-write
		STATUS      current
		DESCRIPTION
		"This value indicates the status of the information on BCCH.
		This value shall be changed each time the information on BCCH,
		except for the contents of the SI-13 message, is changed."
		DEFVAL {0}
		::= {btsGsOptionPackage 15}

	siChangeField OBJECT-TYPE
		SYNTAX      SiChangeField			-- INTEGER (0..15)
		MAX-ACCESS  read-write
		STATUS      current
		DESCRIPTION
		"This value means the representation of which information
		was	changed at the last indication in BCCH_CHANGE_MARK."
		DEFVAL {0}
		::= {btsGsOptionPackage 16}


btsGsInterfacePackage	OBJECT IDENTIFIER
-- 	DESCRIPTION
-- 		"The GP10 interface parameters to support gprs."
	::= {gp10GprsMib 3}
 
rss		OBJECT IDENTIFIER
-- 	DESCRIPTION
-- 		"Radio SubSystem Link Control Params 
--		 The parameters employed to control the radio links for GPRS"
	::= {btsGsInterfacePackage 1}
      
    gprsMsTxpwrMaxCch	OBJECT-TYPE
	    SYNTAX	INTEGER (0..31)
	    MAX-ACCESS	read-write
	    STATUS	current
	    DESCRIPTION
		"The maximum TX power level an MS may use 
		when accessing the system."
		DEFVAL
		{30}
	    ::= {rss 1}

	gprsRexLevAccessMin  OBJECT-TYPE
	    SYNTAX	INTEGER (0..63)
	    MAX-ACCESS	read-write
	    STATUS	current
	    DESCRIPTION
		"Minimum received signal level at the MS 
		required for access to the system.."  
		DEFVAL
		{10}
		::= {rss 2}

    gprsReselectOffset		OBJECT-TYPE
	    SYNTAX	INTEGER (0..31)
	    MAX-ACCESS	read-write
	    STATUS	current
	    DESCRIPTION
		"Applies an offset and hysteresis to the C32 
		re-selection criterion.
		-52, -48,? -12, -10,? 12, 16, ?8."
		DEFVAL
		{0}
	    ::= {rss 3}  

    priorityClass		OBJECT-TYPE
	    SYNTAX	INTEGER (0..7)
	    MAX-ACCESS	read-write
	    STATUS	current
	    DESCRIPTION
		"The HCS Priority for the cells.
		0 Packet Access is not allowed in the cell.
		1 Spare, shall be interpreted as 0
		2 Spare, shall be interpreted as 0
		3 packet access is allowed for priority level 1
		4 packet access is allowed for priority level 1 to 2
		5 packet access is allowed for priority level 1 to 3
		6 packet access is allowed for priority level 1 to 4
		7 spare, shall be interpreted as 6"
		DEFVAL {0}
	    ::= {rss 4}	    

    lsaId		OBJECT-TYPE
	    SYNTAX	INTEGER 
	    MAX-ACCESS	read-write
	    STATUS	current
	    DESCRIPTION
		"The LSA Identities for the cell"
	    ::= {rss 5}

    hcsThreshold		OBJECT-TYPE
	    SYNTAX	INTEGER (0..31)
	    MAX-ACCESS	read-write
	    STATUS	current
	    DESCRIPTION
		"HCS signal level threshold
		-110, -108,? -48"
	    ::= {rss 6}
	    	    	    
    gprsTemporaryOffset		OBJECT-TYPE
	    SYNTAX	INTEGER (0..7)
	    MAX-ACCESS	read-write
	    STATUS	current
	    DESCRIPTION
		"Applies a negative offset 
		to C32 for the duration of PENALTY_TIME.
		0, 10,..., 60 dB, infinity"
	    ::= {rss 7}

    gprsPenaltyTime		OBJECT-TYPE
	    SYNTAX	INTEGER (0..31)
	    MAX-ACCESS	read-write
	    STATUS	current
	    DESCRIPTION
		"Gives the duration for which 
		the temporary offset is applied. 
		10, 20,..., 320 seconds"
	    ::= {rss 8}	    	    	    	    
	
	gprsCellReselectHysteresis	OBJECT-TYPE
	    SYNTAX	INTEGER (0..7)
	    MAX-ACCESS	read-write
	    STATUS	current
	    DESCRIPTION
		"Additional hysteresis applied in Ready state 
		for cells in the same RA. 
		0, 2,..., 14 dB"
		DEFVAL
		{4}
	    ::= {rss 9}

	gprsRaReselectHysteresis	OBJECT-TYPE
	    SYNTAX	INTEGER (0..7)
	    MAX-ACCESS	read-write
	    STATUS	current
	    DESCRIPTION
		"Additional hysteresis applied for 
		cells in different RAs. 
		0, 2,..., 14 dB"
		DEFVAL
		{4}
	    ::= {rss 10}   
	    
	c32Qual	    OBJECT-TYPE
	    SYNTAX	Boolean
	    MAX-ACCESS	read-write
	    STATUS	current
	    DESCRIPTION
		"Flag indicating an exception rule for 
		GPRS_RESELECT_OFFSET." 
	    ::= {rss 11}   

	c31Hysteresis	OBJECT-TYPE
	    SYNTAX	Boolean
	    MAX-ACCESS	read-write
	    STATUS	current
	    DESCRIPTION
		"Flag indicating if hysteresis shall be applied to C31."
	    ::= {rss 12}

	alpha	OBJECT-TYPE
	    SYNTAX	INTEGER (0..10)
	    MAX-ACCESS	read-write
	    STATUS	current
	    DESCRIPTION
		"This field is a binary representation of the paremeter for MS
		output Power control in units of 0.1.
		0,0.1,...,1"
		DEFVAL
		{10}
	    ::= {rss 13}

	pB		OBJECT-TYPE
	    SYNTAX	INTEGER (0..15)
	    MAX-ACCESS	read-write
	    STATUS	current
	    DESCRIPTION
		"Power reduction used by BTS on 
		PBCCH blocks, relatively to the output 
		power used on BCCH 
		0, -2,..., -30 dB"
	    ::= {rss 14}

	networkControlOrder	OBJECT-TYPE
	    SYNTAX	INTEGER (0..3)
	    MAX-ACCESS	read-write
	    STATUS	current
	    DESCRIPTION
		"Controls cell re-selection and measurement reporting
		0 NC0: MS controlled cell re-selection, no measurement reporting,
		1 NC1: MS controlled cell re-selection, MS sends measurement reports
		2 NC2: Network controlled cell re-selection, MS sends measurement reports
		3 Reserved for future use, interpreted as NC0 by mobile station."
		DEFVAL {1}
	    ::= {rss 15}

	ncFrequencyListTable	OBJECT-TYPE  -- need to revisit
	    SYNTAX	SEQUENCE OF NcFrequencyListEntry
	    MAX-ACCESS	not-accessible
	    STATUS	current
	    DESCRIPTION
		"This entry is required to define a table of values.
		Frequency list for cell re-selection 
		measurement reporting"
	    ::= {rss 16}

	ncFrequencyListEntry	OBJECT-TYPE
	    SYNTAX	NcFrequencyListEntry
	    MAX-ACCESS	not-accessible
	    STATUS	current
	    DESCRIPTION
		"This attribute defines the set of radio frequencies
		 available to a cell."
	    INDEX	{ncFrequencyListIndex}  
	    --DEFAULT cookie MIBT_%n
	    ::= {ncFrequencyListTable 1}

	NcFrequencyListEntry	::= SEQUENCE {
	    ncFrequencyListIndex		INTEGER (0..15),
	    ncFrequency		AbsoluteRFChannelNo
	}

	ncFrequencyListIndex	OBJECT-TYPE
	    SYNTAX	INTEGER (0..15)
	    MAX-ACCESS	read-only
	    STATUS	current
	    DESCRIPTION
		"This attribute is used as the index to this table. It
		 is a sequential number between 0 and 15."
	    ::= {ncFrequencyListEntry 1}

	ncFrequency	OBJECT-TYPE
	    SYNTAX	AbsoluteRFChannelNo
	    MAX-ACCESS	read-write
	    STATUS	current
	    DESCRIPTION
		"This attribute contains the absolute radio frequency channel
		number of the PBCCH channel of adjacent cells." 
	   ::= {ncFrequencyListEntry 2}

	ncReportingPeriodI		OBJECT-TYPE
	    SYNTAX	INTEGER (0..7)
	    MAX-ACCESS	read-write
	    STATUS	current
	    DESCRIPTION
		"Time period for measurement reporting
		0.48, 0.96, 1.92, ..., 61.44 seconds"
	   ::= {rss 17}

	ncReportingPeriodT		OBJECT-TYPE
	    SYNTAX	INTEGER (0..7)
	    MAX-ACCESS	read-write
	    STATUS	current
	    DESCRIPTION
		"Time period for measurement reporting
		0.48, 0.96, 1.92, ..., 61.44 seconds"
	   ::= {rss 18}
	   
	extMeasurementOrder	OBJECT-TYPE
	    SYNTAX	INTEGER (0..3)
	    MAX-ACCESS	read-write
	    STATUS	current
	    DESCRIPTION
		"Controls extended measurement reporting."
	   ::= {rss 19}

	extReportingPeriod	OBJECT-TYPE
	    SYNTAX	INTEGER (0..7)
	    MAX-ACCESS	read-write
	    STATUS	current
	    DESCRIPTION
		"Time period for measurement reporting
		60, 120, 240,..., 7680 seconds"
	   ::= {rss 20}

	extReportingType	OBJECT-TYPE
	    SYNTAX	INTEGER (1..3)
	    MAX-ACCESS	read-write
	    STATUS	current
	    DESCRIPTION
		"Defines the type of extended measurement report."
	   ::= {rss 21}

	intFrequency	OBJECT-TYPE
	    SYNTAX	INTEGER (0..31)
	    MAX-ACCESS	read-write
	    STATUS	current
	    DESCRIPTION
		"Frequency for which the MS shall include 
		interference measurements in extended 
		measurement report type 3."
	   ::= {rss 22}

	nccPermitted	OBJECT-TYPE
	    SYNTAX	INTEGER 
	    MAX-ACCESS	read-write
	    STATUS	current
	    DESCRIPTION
		"Bit map of NCC part of BSIC for which 
		the MS shall report extended measurements."
	   ::= {rss 23}   
	   
	pcMeasChan	OBJECT-TYPE
	    SYNTAX	INTEGER  (0..1)
	    MAX-ACCESS	read-write
	    STATUS	current
	    DESCRIPTION
		"Flag that indicates whether the downlink 
		measurements for power control shall be made 
		on BCCH or PDCH.."     
		DEFVAL {1}
	   ::= {rss 24}	
	   
	tavgW		OBJECT-TYPE
	    SYNTAX	INTEGER  (0..25)
	    MAX-ACCESS	read-write
	    STATUS	current
	    DESCRIPTION
		"Signal level filter period for power control 
		in packet idle mode2(k/2)/ 6 multiframes, 
		k = 0,1,..., 25"     
		DEFVAL {15}
	   ::= {rss 25}	
	   
	tavgT		OBJECT-TYPE
	    SYNTAX	INTEGER  (0..25)
	    MAX-ACCESS	read-write
	    STATUS	current
	    DESCRIPTION
		"Signal level filter period for power control 
		in packet transfer mode2(k/2)/ 6 multiframes, 
		k = 0,1,..., 25"     
		DEFVAL {5}
	   ::= {rss 26}
	   
	navgI		OBJECT-TYPE
	    SYNTAX	INTEGER  (0..15)
	    MAX-ACCESS	read-write
	    STATUS	current
	    DESCRIPTION
		"Interference signal level filter constant for 
		power control 2(k/2), 
		k = 0,1,..., 15"     
		DEFVAL {4}
	   ::= {rss 27}	   	  

	gprsMsTargetPower	OBJECT-TYPE
	    SYNTAX	RxLev
	    MAX-ACCESS	read-write
	    STATUS	current
	    DESCRIPTION
		"open loop power control is employed, telling the 
		MS to assume a balanced link and adjust its transmitted 
		power to meet the desired target at the GP. 
		A target is send to the MS in the form of a power control 
		value, gamma, which is computed based on MS_GPRS_TARGET_POWER 
		using the formula in 05.08."
		DEFVAL {30}
	   ::= {rss 28}	     
	   
	spgcCcchSup		OBJECT-TYPE
	    SYNTAX	Boolean
	    MAX-ACCESS	read-write
	    STATUS	current
	    DESCRIPTION
		"This field indicates the support of the parameter SPLIT_PG_CYCLE
		on CCCH on the network side
		0 SPLIT_PG_CYCLE is not supported on CCCH in this cell
		1 SPLIT_PG_CYCLE is supported on CCCH in this cell."
	   ::= {rss 29}	   
	   
rlcMac		OBJECT IDENTIFIER
-- 	DESCRIPTION
-- 		"Radio Link Control Params 
--		 The parameters employed to control the radio links for GPRS"
	::= {btsGsInterfacePackage 2}
      
    t3169	OBJECT-TYPE
	    SYNTAX	INTEGER (1..30)
	    MAX-ACCESS	read-write
	    STATUS	current
	    DESCRIPTION
		"Wait for Reuse of USF and TFI after the mobile station 
		uplink assignment is invalid.Defines when the current 
		uplink assignment is surely invalid on the mobile station 
		side so that the assigned USF(s) and TFI can be reused on 
		the uplink. During that period the corresponding USF(s) is 
		not broadcast. "    
		DEFVAL {5}
	    ::= {rlcMac 1}  

    t3191	OBJECT-TYPE
	    SYNTAX	INTEGER (1..30)
	    MAX-ACCESS	read-write
	    STATUS	current
	    DESCRIPTION
		"Wait for reuse of TFI after sending of the last RLC Data 
		BlockDefines when the current assignment is surely invalid 
		on the mobile station side so that the TFI can be reused."    
		DEFVAL {5}
	    ::= {rlcMac 2}
	    
    t3193	OBJECT-TYPE
	    SYNTAX	INTEGER 
	    MAX-ACCESS	read-write
	    STATUS	current
	    DESCRIPTION
		"Wait for reuse of TFI after reception of the final Packet 
		Downlink Ack/Nack from the mobile station.Defines when 
		timer T3192 on the mobile station side has surely expired 
		so that the TFI can be reused."    
		DEFVAL
		{5}
	    ::= {rlcMac 3}
	    
    t3195	OBJECT-TYPE
	    SYNTAX	INTEGER (1..30)
	    MAX-ACCESS	read-write
	    STATUS	current
	    DESCRIPTION
		"Wait for reuse of TFI when there is no response from 
		the MS (radio failure or cell change)Defines when the 
		current assignment is surely invalid on the mobile 
		station side so that the TFI can be reused."    
		DEFVAL {5}
	    ::= {rlcMac 4}

bssgp OBJECT IDENTIFIER
-- 	DESCRIPTION
-- 		"Bssgp parameters."
	::= {btsGsInterfacePackage 3}	          
	
	blockTimer	OBJECT-TYPE
	    SYNTAX	INTEGER (1..30)
	    MAX-ACCESS	read-write
	    STATUS	current
	    DESCRIPTION
		"Timer Value that guards the blocking or
		unblocking procedures."
		DEFVAL
		{10}
		::= {bssgp 1}	    	    	 
	    	    	    	    	                       
	resetTimer	OBJECT-TYPE
	    SYNTAX	INTEGER (1..120)
	    MAX-ACCESS	read-write
	    STATUS	current
	    DESCRIPTION
		"Timer Value that guards the reset
		procedure."
		DEFVAL
		{60}
		::= {bssgp 2}	

	suspendTimer	OBJECT-TYPE
	    SYNTAX	INTEGER (1..10)
	    MAX-ACCESS	read-write
	    STATUS	current
	    DESCRIPTION
		"Timer Value that guards the suspend
		procedure."
		DEFVAL
		{5}
		::= {bssgp 3}	

	resumeTimer	OBJECT-TYPE
	    SYNTAX	INTEGER (1..10)
	    MAX-ACCESS	read-write
	    STATUS	current
	    DESCRIPTION
		"Timer Value that guards the resume
		procedure."
		DEFVAL
		{5}
		::= {bssgp 4}	

	capUpdateTimer	OBJECT-TYPE
	    SYNTAX	INTEGER (1..30)
	    MAX-ACCESS	read-write
	    STATUS	current
	    DESCRIPTION
		"Timer Value that guards the 
		RA_CAPABILITY_UPDATE procedure."
		DEFVAL
		{10}
		::= {bssgp 5}	
		
	blockRetries	OBJECT-TYPE
	    SYNTAX	INTEGER
	    MAX-ACCESS	read-write
	    STATUS	current
	    DESCRIPTION
		"Number of BSSGP Virtual Connection
		(BVC) Block Retries."
		DEFVAL
		{3}
		::= {bssgp 6}			
		
	unBlockRetries	OBJECT-TYPE
	    SYNTAX	INTEGER
	    MAX-ACCESS	read-write
	    STATUS	current
	    DESCRIPTION
		"Number of BSSGP Virtual Connection
		(BVC) UnBlock Retries."
		DEFVAL
		{3}
		::= {bssgp 7}			

	resetRetries	OBJECT-TYPE
	    SYNTAX	INTEGER
	    MAX-ACCESS	read-write
	    STATUS	current
	    DESCRIPTION
		"Number of BSSGP Virtual Connection
		(BVC) Reset Retries."
		DEFVAL
		{3}
		::= {bssgp 8}				
		
	suspendRetries	OBJECT-TYPE
	    SYNTAX	INTEGER
	    MAX-ACCESS	read-write
	    STATUS	current
	    DESCRIPTION
		"Number of BSSGP Virtual Connection
		(BVC) Suspend Retries."
		DEFVAL
		{3}
		::= {bssgp 9}		
		
	resumeRetries	OBJECT-TYPE
	    SYNTAX	INTEGER
	    MAX-ACCESS	read-write
	    STATUS	current
	    DESCRIPTION
		"Number of BSSGP Virtual Connection
		(BVC) Resume Retries."
		DEFVAL
		{3}
		::= {bssgp 10}		
		
	raCapUpdateRetries	OBJECT-TYPE
	    SYNTAX	INTEGER
	    MAX-ACCESS	read-write
	    STATUS	current
	    DESCRIPTION
		"Number of BSSGP Virtual Connection
		(BVC) RA-CAPABILITY-UPDATE Retries."
		DEFVAL
		{3}
		::= {bssgp 11}		

	timeInterval	OBJECT-TYPE
	    SYNTAX	INTEGER (5..6000)
	    MAX-ACCESS	read-write
	    STATUS	current
	    DESCRIPTION
		"Interval after Flow Control MS before
		SGSN may use SGSN generated Bmax and R."
		DEFVAL
		{10}
		::= {bssgp 12}    

	networkPort		OBJECT-TYPE
	    SYNTAX	INTEGER (1024..65535)
	    MAX-ACCESS	read-write
	    STATUS	current
	    DESCRIPTION
		"Base UDP port for Network QOS levels."  
		DEFVAL {22240}
		::= {bssgp 13}
		
		
btsGsMeasPackage	OBJECT IDENTIFIER
-- 	DESCRIPTION
-- 		"The GP10 measurement parameters to support gprs."
	::= {gp10GprsMib 4}  
	
	flushReqRecvd		OBJECT-TYPE
	    SYNTAX	INTEGER 
	    MAX-ACCESS	read-only
	    STATUS	current
	    DESCRIPTION
		"This measurement provides the total number of 
		flush request messages received from the SGSN to 
		flush the PDUs for a given cell"
		::= {btsGsMeasPackage 1}  

	pagingReqRecvd		OBJECT-TYPE
	    SYNTAX	INTEGER 
	    MAX-ACCESS	read-only
	    STATUS	current
	    DESCRIPTION
		"This measurement provides the total number of 
		PAGING messages received by the BSS from the SGSN"
		::= {btsGsMeasPackage 2}
		
	meanPsInterArrivalTime		OBJECT-TYPE
	    SYNTAX	INTEGER
	    MAX-ACCESS	read-only
	    STATUS	current
	    DESCRIPTION
		"This measurement provides the arithmetic mean of 
		the sum of time intervals between consecutive mobile 
		originating packet channel access request.
		This measurement is obtained by accumulating the 
		time segments between receipt of consecutive 
		'PACKET CHANNEL REQUEST' message with the establishment 
		cause being either one phase packet access or single 
		block packet access, on the PRACH and then taking the 
		arithmetic mean"
		::= {btsGsMeasPackage 3}
		
	availablePdch		OBJECT-TYPE
	    SYNTAX	Gauge
	    MAX-ACCESS	read-only
	    STATUS	current
	    DESCRIPTION
		"This measurement provides the current number 
		of PDCHs which are available to be used.
		The gauge will be incremented when the PDCH becomes 
		available and decremented when it becomes unavailable"
		::= {btsGsMeasPackage 4}
		
	meanAvailablePdch		OBJECT-TYPE
	    SYNTAX	Gauge
	    MAX-ACCESS	read-only
	    STATUS	current
	    DESCRIPTION
		"This measurement provides the mean number of PDCHs that 
		are available to be used (including those actually in use) 
		over the measured period.
		The gauge will be incremented when the PDCH becomes available 
		and decremented when it becomes unavailable"
		::= {btsGsMeasPackage 5}
		
	maxAvailablePdch		OBJECT-TYPE
	    SYNTAX	Gauge
	    MAX-ACCESS	read-only
	    STATUS	current
	    DESCRIPTION
		"This measurement provides the maximum number of PDCHs which 
		are available to be used (including those actually in use) 
		over the measured period.
		The gauge will be incremented when the PDCH becomes available 
		and decremented when it becomes unavailable"
		::= {btsGsMeasPackage 6}
		
	minAvailablePdch		OBJECT-TYPE
	    SYNTAX	Gauge
	    MAX-ACCESS	read-only
	    STATUS	current
	    DESCRIPTION
		"This measurement provides the minimum number of PDCHs 
		which are available to be used (including those actually 
		in use) over the measured period
		The gauge will be incremented when the PDCH becomes available 
		and decremented when it becomes unavailable"
		::= {btsGsMeasPackage 7}
		
	meanOccupiedPdch		OBJECT-TYPE
	    SYNTAX	INTEGER
	    MAX-ACCESS	read-only
	    STATUS	current
	    DESCRIPTION
		"This measurement provides the arithmetic mean number of 
		occupied PDCHs
		This measurement is obtained by sampling the number of PDCHs 
		that are carrying packet traffic at a pre-defined interval 
		(System designed), and then taking the arithmetic mean."
		::= {btsGsMeasPackage 8}
		
	maxOccupiedPdch		OBJECT-TYPE
	    SYNTAX	Gauge
	    MAX-ACCESS	read-only
	    STATUS	current
	    DESCRIPTION
		"This measurement provides the highest recorded value 
		for the number occupied by PDCHs
		This measurement is obtained by sampling at a pre-defined 
		interval (System designed), the maximum number of PDCHs 
		which are carrying packet traffic"
		::= {btsGsMeasPackage 9}
		
	minOccupiedPdch		OBJECT-TYPE
	    SYNTAX	Gauge
	    MAX-ACCESS	read-only
	    STATUS	current
	    DESCRIPTION
		"This measurement provides the lowest 
		recorded value for the number of occupied PDCHs
		This measurement is obtained by sampling at a 
		pre-defined interval (System designed), the maximum 
		number of PDCHs which are carrying packet traffic"
		::= {btsGsMeasPackage 10}
		
	availablePdchAllocTime	OBJECT-TYPE
	    SYNTAX	INTEGER 
	    MAX-ACCESS	read-only
	    STATUS	current
	    DESCRIPTION
		"This measurement gives the total amount of time 
		in the granularity period, where all PDCHs were allocated
		This time is computed with starting time when the last PDCH is 
		assigned and the end time when a PDCH is first released"
		::= {btsGsMeasPackage 11}
		
	packetPagingMessages		OBJECT-TYPE
	    SYNTAX	INTEGER 
	    MAX-ACCESS	read-only
	    STATUS	current
	    DESCRIPTION
		"This measurement provides the number of Packet Paging messages 
		transmitted over PCCCH (these are counted as attempts)"
		::= {btsGsMeasPackage 12}
		
	pagchQueueLength		OBJECT-TYPE
	    SYNTAX	INTEGER
	    MAX-ACCESS	read-only
	    STATUS	current
	    DESCRIPTION
		"This measurement provides the arithmetic mean of the number 
		of all messages waiting for transmission on the PPCH-PAGCH 
		sub channel on the PCCCH
		  This measurement is obtained by sampling at a pre-defined 
		  interval (System designed), the PPCH-PAGCH queue length and 
		  then taking the arithmetic mean"
		::= {btsGsMeasPackage 13}
		
	pagesDiscardedFromPpch	OBJECT-TYPE
	    SYNTAX	INTEGER
	    MAX-ACCESS	read-only
	    STATUS	current
	    DESCRIPTION
		"This measurement provides the number of Packet Paging messages 
		which are discarded from the PPCH queue before they could be 
		transmitted on PCCCH"
		::= {btsGsMeasPackage 14}
		
	assignmentRequest		OBJECT-TYPE
	    SYNTAX	INTEGER 
	    MAX-ACCESS	read-only
	    STATUS	current
	    DESCRIPTION
		"This measurement provides the number of packet 
		channel assignment requests, per cause"
		::= {btsGsMeasPackage 15}
		
	succAssignmentProc	OBJECT-TYPE
	    SYNTAX	INTEGER
	    MAX-ACCESS	read-only
	    STATUS	current
	    DESCRIPTION
		"This measurement provides the number of 
		successful packet channel assignment procedures, 
		per cause
		Note: A packet channel assignment is considered 
		successful when either the 'PACKET UPLINK ASSIGNMENT' 
		message or the 'IMMEDIATE ASSIGNMENT COMMAND' 
		message is sent"
		::= {btsGsMeasPackage 16}
		
	succPdtchSeizures		OBJECT-TYPE
	    SYNTAX	INTEGER
	    MAX-ACCESS	read-only
	    STATUS	current
	    DESCRIPTION
		"This measurement provides the number of successful 
		PDTCH seizures"
		::= {btsGsMeasPackage 17}	
		
	meanPacketQueueLength		OBJECT-TYPE
	    SYNTAX	INTEGER 
	    MAX-ACCESS	read-only
	    STATUS	current
	    DESCRIPTION
		"This measurement provides the arithmetic mean of the 
		number of all messages waiting for transmission on the PDTC"
		::= {btsGsMeasPackage 18}

	serviceChanges		OBJECT-TYPE
	    SYNTAX	INTEGER 
	    MAX-ACCESS	read-only
	    STATUS	current
	    DESCRIPTION
		"With service upgrade and downgrade it is meant a switch 
		from the used coding scheme (CS1, CS2,...) to another one. 
		This measurement counts the number of these upgrades / 
		downgrades per cell"
		::= {btsGsMeasPackage 19}


	cdrClientSSLEnable	OBJECT-TYPE
	    SYNTAX	Boolean
	    MAX-ACCESS	read-write
	    STATUS	current
	    DESCRIPTION
		"Flag to turn on/off SSL encryption between GP10 and GMC for CDR delivery"
		DEFVAL	{0}
	   ::= {gp10CdrMib 1}


	cdrLongCallTimer 	OBJECT-TYPE
	    SYNTAX	INTEGER (1..30)
	    MAX-ACCESS	read-write
	    STATUS	current
	    DESCRIPTION
		"Timer to trigger CDR generation for long calls. 

		Unit: 1 minute
                "
	    DEFVAL {10}
	   ::= {gp10CdrMib 2}



	t101 OBJECT-TYPE
		SYNTAX	HandoverTimer
		MAX-ACCESS	read-write
		STATUS	current
		DESCRIPTION
		"
		This timer supervises the queuing time for a free channel at anchor GP10 but is not implemented yet. 
		UNIT: 10ms
		Refer to GSM03.09
		"
		DEFVAL {200}
	::= { handoverTimerMib 1}


	t102 OBJECT-TYPE
		SYNTAX	HandoverTimer
		MAX-ACCESS	read-write
		STATUS	current
		DESCRIPTION
		"
		This timer supervises the time for handover completion for both inter-GP and external handover.
        UNIT: 10ms
		Refer to GSM03.09
		"
		DEFVAL {500}
	::= { handoverTimerMib 2}

	t103 OBJECT-TYPE
		SYNTAX	HandoverTimer
		MAX-ACCESS	read-write
		STATUS	current
		DESCRIPTION
		"
		Handover - waiting for Target Ho Complt (ANCH)
		UNIT: 10ms
		"
		DEFVAL {2000}
	::= { handoverTimerMib 3}

	t104 OBJECT-TYPE
		SYNTAX	HandoverTimer
		MAX-ACCESS	read-write
		STATUS	current
		DESCRIPTION
		"
		Handover - waiting for Mobile Handover Complt (ANCH)
		UNIT: 10ms
		"
		DEFVAL {2000}
	::= { handoverTimerMib 4}

	t201 OBJECT-TYPE
		SYNTAX	HandoverTimer
		MAX-ACCESS	read-write
		STATUS	current
		DESCRIPTION
		"
		This timer supervises the queuing time for a free channel at target GP10 but is not implemented yet 
		UNIT: 10ms 
		Refer to GSM03.09
		"
		DEFVAL {200}
	::= { handoverTimerMib 5}

	t202 OBJECT-TYPE
		SYNTAX	HandoverTimer
		MAX-ACCESS	read-write
		STATUS	current
		DESCRIPTION
		"
		Handover - waiting for Mobile Handover Complt btw BSSs under MSC-B
		UNIT: 10ms
		"
		DEFVAL {500}
	::= { handoverTimerMib 6}

	t204 OBJECT-TYPE
		SYNTAX	HandoverTimer
		MAX-ACCESS	read-write
		STATUS	current
		DESCRIPTION
		"
		Handover - waiting for Mobile Handover Complt (TRG)
		UNIT: 10ms
		"
		DEFVAL {2000}
	::= { handoverTimerMib 7}

	t210 OBJECT-TYPE
		SYNTAX	HandoverTimer
		MAX-ACCESS	read-write
		STATUS	current
		DESCRIPTION
		"
		This timer is used to supervise the time for establishing a circuit connection from PLMN to MNET
        where the call is being handed over to MNET 
		UNIT:10ms 
		Refer to GSM03.09
		"
		DEFVAL {500}
	::= { handoverTimerMib 8}

	t211 OBJECT-TYPE
		SYNTAX	HandoverTimer
		MAX-ACCESS	read-write
		STATUS	current
		DESCRIPTION
		"
		Handover - waiting for Mobile Handover Complt or Failure (TRG)
		UNIT: 10ms
		"
		DEFVAL {2000}
	::= { handoverTimerMib 9}




--
-- GP10 Service Status MIB
--

	snmpServiceEnabled	OBJECT-TYPE
		SYNTAX          OperationalState
		MAX-ACCESS      read-only
		STATUS          current
		DESCRIPTION
		"Indicates the status of SNMP service."
		::= { gp10ServiceStatusMib 1 }

	httpServiceEnabled	OBJECT-TYPE
		SYNTAX          OperationalState
		MAX-ACCESS      read-only
		STATUS          current
		DESCRIPTION
		"Indicates the status of HTTP service."
		::= { gp10ServiceStatusMib 2 }

	telnetServiceEnabled	OBJECT-TYPE
		SYNTAX          OperationalState
		MAX-ACCESS      read-only
		STATUS          current
		DESCRIPTION
		"Indicates the status of Telnet service."
		::= { gp10ServiceStatusMib 3 }

	sshServiceEnabled	OBJECT-TYPE
		SYNTAX          OperationalState
		MAX-ACCESS      read-only
		STATUS          current
		DESCRIPTION
		"Indicates the status of SSH service."
		::= { gp10ServiceStatusMib 4 }

	ftpServiceEnabled	OBJECT-TYPE
		SYNTAX          OperationalState
		MAX-ACCESS      read-only
		STATUS          current
		DESCRIPTION
		"Indicates the status of FTP service."
		::= { gp10ServiceStatusMib 5 }

		
END
